HPI-MIB DEFINITIONS ::= BEGIN

IMPORTS
	MODULE-IDENTITY, 
	OBJECT-TYPE,
	NOTIFICATION-TYPE,
	Unsigned32,
	Counter32,
	Counter64  		FROM SNMPv2-SMI
	TEXTUAL-CONVENTION,
	DateAndTime,
	RowPointer,
	RowStatus,
	TruthValue		FROM SNMPv2-TC
	MODULE-COMPLIANCE, 
	OBJECT-GROUP,
	NOTIFICATION-GROUP	FROM SNMPv2-CONF
	enterprises		FROM RFC1155-SMI;

hpi MODULE-IDENTITY
    LAST-UPDATED "200311111800Z"
    ORGANIZATION "OpenHPI"
    CONTACT-INFO "
		Sean Dague
	      		Postal: IBM
				2455 South Road
				Poughkeepsie, Ny 12601
				US
			Tel:	+1 845 433 2965
			Fax:	+1 845 433 2379
			E-mail: sdague@us.ibm.com

		Tom Hernandez
			Postal:	Motorola Computer Group
				2900 S. Diablo Way
				Tempe, Az 85282
				US
			E-mail:	MCX1243@motorola.com

		Kurt Taylor
			Postal: IBM
				11400 Burnet Rd.
				Austin, Tx 78758
				US
			Tel:    +1 512 838 2496
			E-mail: krtaylor@us.ibm.com

		Konrad Rzeszutek
	       		Postal: IBM
				1 Rogers St
				Cambridge, Ma 02142
				US
			Tel:	+1 617 693 1718
			E-mail: konradr@us.ibm.com
        "
    DESCRIPTION
	"This MIB defines the HPI instrumentation based on
	'Service Availability Forum Hardware Platform Interface'
	(SA-HPI-A.01.01).

	This MIB module defines a set of objects that allow the 
         management of entities on a variety of hardware platforms.  The  
         abstractions presented in this MIB are derived from the 
                  Service Availability Forum Hardware Platform Interface 
                  specification version 01.01.
           
         The MIB views a hardware platform as a collection of physical 
                  entities that can be managed individually.  A logical 
                  collection of entities comprises a management domain.

         Each entity has a common set of attributes reflected in the 
         entity table.  Entities may have additional categorical 
                  attributes that may exist in one or more of the hotswap 
                  table, control table, sensor table, watchdog table,
		  inventory control table and config table.

         The hotswap table defines management attributes
         for an entity that supports hotswap, generally referred to as 
                  a FRU.

         The controls table defines variables for reading and setting 
                  controls associated with an entity.

         The sensors table defines variables for reading sensors 
                  associated with an entity as well as controlling event 
                  generation for that sensor.

	The watchdog table defines variables for reading watchdog
		  associated with an entitry.

	The inventory control defines variables for reading inventory
		resources.  
    
	This MIB is version 1.3.1"

    REVISION	"200311240000Z" 
    DESCRIPTION 
	"Changed HotSwap table column names."
    REVISION	"200401190000Z"
    DESCRIPTION
	"Changed saHpiCtrlAttributes to be less confusing."
    REVISION	"200402080000Z"
    DESCRIPTION
	"Changed HPI MIB OID to the one SAF ratified."
	::= { enterprises 18568 1 1 1 }

hpiEntity	OBJECT IDENTIFIER ::= { hpi 1 }



HpiTimeStamp ::= TEXTUAL-CONVENTION
    	STATUS       current
    	DESCRIPTION
	"
 An HPI time value represents the local time as the number of nanoseconds
 from 00:00:00, January 1, 1970, in a 64-bit signed integer. This format
 is sufficient to represent times with nano-second resolution from the
 year 1678 to 2262. Every API which deals with time values must define
 the timezone used.

 It should be noted that although nano-second resolution is supported
 in the data type, the actual resolution provided by an implementation
 may be more limited than this.

 The value -263, which is 0x8000000000000000, is used to indicate
 'unknown/unspecified time'.

 Conversion to/from POSIX and other common time representations is
 relatively straightforward. The following code framgment converts
 between SaHpiTimeT and time_t:

     time_t tt1, tt2;
     SaHpiTimeT saHpiTime;

     time(&tt1);
     saHpiTime = (SaHpiTimeT) tt1  1000000000;
     tt2 = saHpiTime / 1000000000;

The following fragment converts between SaHpiTimeT and a struct timeval:

     struct timeval tv1, tv2;
     SaHpiTimeT saHpiTime;

     gettimeofday(&tv1, NULL);
     saHpiTime = (SaHpiTimeT) tv1.tv_sec  1000000000 + tv1.tv_usec  1000;
     tv2.tv_sec = saHpiTime / 1000000000;
     tv2.tv_usec = saHpiTime % 1000000000 / 1000;

 The following fragment converts between SaHpiTimeT and a struct timespec:

     struct timespec ts1, ts2;
     SaHpiTimeT saHpiTime;

     clock_gettime(CLOCK_REALTIME, &ts1);
     saHpiTime = (SaHpiTimeT) ts1.tv_sec  1000000000 + ts1.tv_nsec;
     ts2.tv_sec = saHpiTime / 1000000000;
     ts2.tv_nsec = saHpiTime % 1000000000;

 Note, however, that since time_t is (effectively) universally 32 bits,
 all of these conversions will cease to work on January 18, 2038.

 Some subsystems may need the flexibility to report either absolute or
 relative (eg. to system boot) times. This will typically be in the
 case of a board which may or may not, depending on the system setup,
 have an idea of absolute time. For example, some boards may have
 'time of day' clocks which start at zero, and never get set to the
 time of day.

 In these cases, times which represent 'current' time (in events, for
 example) can be reported based on the clock value, whether it has been
 set to the actual date/time, or whether it represents the elapsed time
 since boot. If it is the time since boot, the value will be (for 27
 years) less than 0x0C00000000000000, which is Mon May 26 16:58:48 1997.
 If the value is greater than this, then it can be assumed to be an
 absolute time.

 Every API which can report either absolute or relative times must
 state this rule clearly in its interface specification.

 SAHPI_TIME_UNSPECIFIED     0x8000000000000000LL

 Maximum time that can be specified as relative :
 SAHPI_TIME_MAX_RELATIVE     0x0C00000000000000LL
"
	SYNTAX	Counter64

--
-- RPT Entry
--

saHpiTable OBJECT-TYPE
	SYNTAX		SEQUENCE OF SaHpiEntry
	MAX-ACCESS	not-accessible
	STATUS		current
	DESCRIPTION	
	"This table represents the management attributes common to all entities
         within the managed platform.  The logical domain ID and the entity ID
         are used to address an entity."
	::= {hpiEntity 4}
	
saHpiEntryCount OBJECT-TYPE
	SYNTAX		Counter32
	MAX-ACCESS	read-only
	STATUS		current
	DESCRIPTION	"The number of RPT entries present in the system. 
	This field is used to determine if new resources have been added
	or existing removed. The same functionality is available using
	notifications."
	::= {hpiEntity 1}

saHpiEntryUpdateCount OBJECT-TYPE
	SYNTAX		Unsigned32
	MAX-ACCESS	read-only
	STATUS		current
	DESCRIPTION	"This count is incremented any time the table
	is changed. It rolls over to zero when the maximum value is reached.
	The same functionality is available using notifications."
	::= {hpiEntity 2}

saHpiEntryUpdateTimestamp OBJECT-TYPE
	SYNTAX		HpiTimeStamp
	MAX-ACCESS	read-only
	STATUS		current
	DESCRIPTION	"This time is set any time the table is changed. 
	If the implementation cannot supply an absolute timestamp, then it may
	supply a timestamp relative to some system-defined epoch, such as 
	system boot. The value SAHPI_TIME_UNSPECIFIED indicates that the 
	time of the update cannot be determined.

	Otherwise, If the value is less than or equal to 
	SAHPI_TIME_MAX_RELATIVE, then it is relative; 
	if it is greater than SAHPI_TIME_MAX_RELATIVE, then it is absolute.

	Unspecified or unknown time  is:
			 SAHPI_TIME_UNSPECIFIED     0x8000000000000000
			
	Maximum time that can be specified as relative:
			 SAHPI_TIME_MAX_RELATIVE    0x0C00000000000000 
			 
	Note: The same functionality - when the table is changed - is available
	via notifications."
	::= {hpiEntity 3}

saHpiEntry OBJECT-TYPE
	SYNTAX		SaHpiEntry
	MAX-ACCESS	not-accessible
	STATUS		current
	DESCRIPTION
		"This structure is used to store the RPT entry information.
		The ResourceCapabilities field definies the capabilities of
		the resource.  This field must be non-zero for all valid
		resources.   The ResourceTag field is an informational value
		that supplies the caller with naming  information for the
		resource. This should be set to the  user-visible  name for a
		resource, which can be used to identify the resource in
		messages to a human operator.  For example, it could be set to
		match a physical printed label attached to the primary  entity
		which the resource manages. See section 5.2.6,
		SaHpiResourceTagSet(), on page 33."
	INDEX	{ saHpiDomainID, saHpiResourceID ,saHpiEntryID }
	::= {saHpiTable 1}

SaHpiEntry ::= SEQUENCE {
	saHpiDomainID		Unsigned32,
	saHpiEntryID		Unsigned32,
	saHpiResourceID		Unsigned32,
	saHpiResourceEntityPath		OCTET STRING,
	saHpiResourceCapabilities	Unsigned32,
	saHpiResourceSeverity		INTEGER,

	saHpiResourceInfoResourceRev		Unsigned32,
	saHpiResourceInfoSpecificVer		Unsigned32,
	saHpiResourceInfoDeviceSupport		Unsigned32,
	saHpiResourceInfoManufacturerId		Unsigned32,
	saHpiResourceInfoProductId		Unsigned32,
	saHpiResourceInfoFirmwareMajorRev	Unsigned32,
	saHpiResourceInfoFirmwareMinorRev	Unsigned32,
	saHpiResourceInfoAuxFirmwareRev		Unsigned32,


	saHpiResourceTagTextType	INTEGER,	
	saHpiResourceTagTextLanguage	INTEGER,
	saHpiResourceTag		OCTET STRING,
	saHpiParamControl		INTEGER,
	saHpiClearEvents		RowStatus,
	saHpiEventLogTime		HpiTimeStamp,
	saHpiEventLogState		INTEGER
	}

saHpiDomainID OBJECT-TYPE 
	SYNTAX		Unsigned32 
	MAX-ACCESS	read-only
	STATUS		current
	DESCRIPTION	
	"The Domain ID is used when the resource is also a domain.
 	The SAHPI_UNSPECIFIED_DOMAIN_ID value may be used by an 
	implementation when populating the ResourceId value for 
	an RPT entry that is a domain only.

	Note:
 		SAHPI_UNSPECIFIED_DOMAIN_ID  0xFFFFFFFF(4294967295) " 
	::= {saHpiEntry 1}

saHpiEntryID OBJECT-TYPE 
	SYNTAX		Unsigned32	
	MAX-ACCESS	read-only
	STATUS		current
	DESCRIPTION	"Entry ID for record"
	::= {saHpiEntry 2}

saHpiResourceID OBJECT-TYPE 
	SYNTAX		Unsigned32
	MAX-ACCESS	read-only
	STATUS		current
	DESCRIPTION	"Resource identifier."
	::= {saHpiEntry 3}

saHpiResourceEntityPath OBJECT-TYPE 
	SYNTAX		OCTET STRING
	MAX-ACCESS	read-only
	STATUS		current
	DESCRIPTION	" 
	If resource manages a FRU, entity path of the FRU.
        If resource manages a single entity, entity path of 
	that entity. 
	If resource manages multiple entities, the entity path 
	of the 'primary' entity managed by the resource.  
	
	Must be set to the same value in every domain which 
	contains this resource.

	This object converts HPI's saHpiEntityPathT structure 
	and an OpenHPI canonical string. The canonical string is 
	formed by removing the SAHPI_ENT_ prefix from the 
	HPI types, and creating tuples for the entity types. 
	
	Order of significance is inverted to make entity paths 
	look more like Unix directory structure. It is also assumed 
	that {ROOT,0} exists implicitly before all of these entries. 
	
	For example:
 	 {SYSTEM_CHASSIS,2}{PROCESSOR_BOARD,0} "

	::= {saHpiEntry 4}

saHpiResourceCapabilities OBJECT-TYPE 
	SYNTAX		Unsigned32 
	MAX-ACCESS	read-only
	STATUS		current
	DESCRIPTION	" 
	Resource Capabilities
			
	This definition defines the capabilities of a given resource. 
	One resource may support any number of capabilities using 
	the bit mask. Every resource must set at least one of 
	these capabilities; ie. zero is not a valid value for a 
	resource's capabilities.
			
	SAHPI_CAPABILITY_DOMAIN           (0x80000000)
	SAHPI_CAPABILITY_RESOURCE         (0X40000000) 
	SAHPI_CAPABILITY_EVT_DEASSERTS	  (0x00008000)
	Indicates that all sensors on the resource have the property 
	that their Assertion and Deassertion event enable flags are 
	the same. That is, for all event states whose assertion 
	triggers an event, it is guaranteed that the deassertion of 
	that event will also trigger an event. Thus, the user may 
	track the state of sensors on the resource by monitoring 
	events rather than polling for state changes.

	SAHPI_CAPABILITY_AGGREGATE_STATUS  (0x00002000) 
	SAHPI_CAPABILITY_CONFIGURATION	   (0x00001000)
	SAHPI_CAPABILITY_MANAGED_HOTSWAP   (0x00000800) 
	Indicates that the resource supports managed hotswap. 
	Since hotswap only makes sense for field-replaceable units, 
	the SAHPI_CAPABILITY_FRU capability bit must also be set 
	for this resource.

	SAHPI_CAPABILITY_WATCHDOG          (0x00000400)
	SAHPI_CAPABILITY_CONTROL           (0x00000200) 
	SAHPI_CAPABILITY_FRU		   (0x00000100)
	Indicates that the resource is a field-replaceable unit; 
	i.e., it is capable of being removed and replaced in a 
	live system. This does not necessarily imply that the 
	resource supports managed hotswap.

	SAHPI_CAPABILITY_INVENTORY_DATA     (0x00000008) 
	SAHPI_CAPABILITY_SEL                (0x00000004) 
	SAHPI_CAPABILITY_RDR		    (0x00000002) 
	Indicates that a resource data record (RDR) repository is 
	supplied by the resource. Since the existence of an RDR is 
	mandatory, this capability must be asserted.         

	SAHPI_CAPABILITY_SENSOR             (0x00000001)"
	::= {saHpiEntry 5}

saHpiResourceSeverity OBJECT-TYPE 
	SYNTAX		INTEGER {
				undefined(0),
        			critical (1),
        			major(2),
        			minor(3),
        			informational(4),
        			ok(5),
        			debug(81)
			}
	MAX-ACCESS	read-write
	STATUS		current
	DESCRIPTION	" Indicates the criticality that should be 
	raised when the resource is not responding.
	
	Note: The enumerated named have +1 added as opposed to the SA HPI 
	spec for the same constants.  "
	::= {saHpiEntry 6}


saHpiResourceInfoResourceRev OBJECT-TYPE 
	SYNTAX		Unsigned32(0..255)
	MAX-ACCESS	read-only
	STATUS		current
	DESCRIPTION	" 
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."

	::= {saHpiEntry 7}

saHpiResourceInfoSpecificVer OBJECT-TYPE 
	SYNTAX		Unsigned32(0..255)
	MAX-ACCESS	read-only
	STATUS		current
	DESCRIPTION	"
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 8}


saHpiResourceInfoDeviceSupport OBJECT-TYPE 
	SYNTAX		Unsigned32(0..255)
	MAX-ACCESS	read-only
	STATUS		current
	DESCRIPTION	" 
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 9}


saHpiResourceInfoManufacturerId OBJECT-TYPE 
	SYNTAX		Unsigned32(0..255)
	MAX-ACCESS	read-only
	STATUS		current
	DESCRIPTION	"
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 10}


saHpiResourceInfoProductId OBJECT-TYPE 
	SYNTAX		Unsigned32
	MAX-ACCESS	read-only
	STATUS		current
	DESCRIPTION	"
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 11}


saHpiResourceInfoFirmwareMajorRev OBJECT-TYPE 
	SYNTAX		Unsigned32(0..255)
	MAX-ACCESS	read-only
	STATUS		current
	DESCRIPTION	"
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 12}

saHpiResourceInfoFirmwareMinorRev OBJECT-TYPE 
	SYNTAX		Unsigned32(0..255)
	MAX-ACCESS	read-only
	STATUS		current
	DESCRIPTION	" 
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 13}


saHpiResourceInfoAuxFirmwareRev OBJECT-TYPE 
	SYNTAX		Unsigned32(0..255)
	MAX-ACCESS	read-only
	STATUS		current
	DESCRIPTION	"
	saHpiResourceInfo contains static configuration data 
	concerning the management controller associated with 
	the resource, or the resource itself. 
	
	Note this information is used to describe the resource; 
	that is, the piece of infrastructure which manages an 
	entity (or multiple entities) - NOT the entities for 
	which the resource provides management. The purpose of the 
	saHpiResourceInfoT structure is to provide information 
	that the HPI user may need in order to interact 
	correctly with the resource (e.g., recognize a 
	specific management controller which may have defined 
	OEM fields in sensors, OEM controls, etc.
	
	All of the fields in the following structure may or 
	may not be used by a given resource."
	::= {saHpiEntry 14}


saHpiResourceTagTextType OBJECT-TYPE 
	SYNTAX		INTEGER {
				undefined(0),
				binary(1), 
				bcdplus(2), 
				ascii6(3),
				language(4)
			}
	MAX-ACCESS	read-write
	STATUS		current
	DESCRIPTION	"Defines the type of data the saHpiResourceTag is
	encoded as:
	 binary(1):
		  String of bytes, any values legal

         bcdplus(2)
		String of 0-9, space, dash, period ONLY

         ascii6(3)
		Reduced ASCII character set: 0x20-0x5F ONLY

         language(4)
		ASCII or UNICODE depending on language
	"
	::= {saHpiEntry 15}

saHpiResourceTagTextLanguage OBJECT-TYPE
	SYNTAX		INTEGER {
				undefined (0),
				unknown (1),
				afar (2),
				abkhazian (3),
				afrikaans (4),
				amharic (5),
				arabic (6),
				assamese (7),
				aymara (8),
				azerbaijani (9),
				bashkir (10),
				byelorussian (11),
				bulgarian (12),
				bihari (13),
				bislama (14),
				bengali (15),
				tibetan (16),
				breton (17),
				catalan (18),
				corsican (19),
				czech (20),
				welsh (21),
				danish (22),
				german (23),
				bhutani (24),
				greek (25),
				english (26),
				esperanto (27),
				spanish (28),
				estonian (29),
				basque (30),
				persian (31),
				finnish (32),
				fiji (33),
				faeroese (34),
				french (35),
				frisian (36),
				irish (37),
				scotsgaelic (38),
				galician (39),
				guarani (40),
				gujarati (41),
				hausa (42),
				hindi (43),
				croatian (44),
				hungarian (45),
				armenian (46),
				interlingua (47),
				interlingue (48),
				inupiak (49),
				indonesian (50),
				icelandic (51),
				italian (52),
				hebrew (53),
				japanese (54),
				yiddish (55),
				javanese (56),
				georgian (57),
				kazakh (58),
				greenlandic (59),
				cambodian (60),
				kannada (61),
				korean (62),
				kashmiri (63),
				kurdish (64),
				kirghiz (65),
				latin (66),
				lingala (67),
				laothian (68),
				lithuanian (69),
				latvianlettish (70),
				malagasy (71),
				maori (72),
				macedonian (73),
				malayalam (74),
				mongolian (75),
				moldavian (76),
				marathi (77),
				malay (78),
				maltese (79),
				burmese (80),
				nauru (81),
				nepali (82),
				dutch (83),
				norwegian (84),
				occitan (85),
				afanoromo (86),
				oriya (87),
				punjabi (88),
				polish (89),
				pashtopushto (90),
				portuguese (91),
				quechua (92),
				rhaetoromance (93),
				kirundi (94),
				romanian (95),
				russian (96),
				kinyarwanda (97),
				sanskrit (98),
				sindhi (99),
				sangro (100),
				serbocroatian (101),
				singhalese (102),
				slovak (103),
				slovenian (104),
				samoan (105),
				shona (106),
				somali (107),
				albanian (108),
				serbian (109),
				siswati (110),
				sesotho (111),
				sudanese (112),
				swedish (113),
				swahili (114),
				tamil (115),
				telugu (116),
				tajik (117),
				thai (118),
				tigrinya (119),
				turkmen (120),
				tagalog (121),
				setswana (122),
				tonga (123),
				turkish (124),
				tsonga (125),
				tatar (126),
				twi (127),
				ukrainian (128),
				urdu (129),
				uzbek (130),
				vietnamese (131),
				volapuk (132),
				wolof (133),
				xhosa (134),
				yoruba (135),
				chinese (136),
				zulu (137)
			}
        MAX-ACCESS      read-write
	STATUS          current
	DESCRIPTION     "
	This enumeration lists all of the languages that can be 
	associated with text.  undefined (0) indicates that 
	the language is unspecified or unknown.  "
	::= {saHpiEntry 16}

saHpiResourceTag	OBJECT-TYPE
	SYNTAX		OCTET STRING(SIZE(0..255))
	MAX-ACCESS	read-write
	STATUS		current
	DESCRIPTION	"Resource tag. The type of date is specified
	by saHpiResourceTagTextType and saHpiResourceTagLanguage."
	::= {saHpiEntry 17}

saHpiParamControl OBJECT-TYPE
	SYNTAX		INTEGER {
				undefined(0),
				restoreDefaultParm(1),
				saveParm(2),
				restoreParm(3)
			}
	MAX-ACCESS	read-write
	STATUS		current
	DESCRIPTION
	"This object allows the user to save and restore parameters 
	associated with a specific resource. Valid actions for this 
	function include:

	undefined(0)	- resource has no concept of 	configurations.

	restoreDefaultParm(1) - Restores the factory default settings 
			for a specific resource. Factory defaults 
			include sensor thresholds and configurations, 
			and resource- specific configuration parameters.
	savaParm(2) - Stores the resource configuration parameters in 
			non-volatile storage. Resource configuration 
			parameters stored in non-volatile storage will 
			survive power cycles and resource resets.
	restoreParm(3) - Restores resource configuration parameters 
			from non-volatile storage. Resource
			configuration parameters include sensor 
			thresholds and sensor configurations, as well 
			as resource-specific."
	REFERENCE
	"Derieved from SA-HPI-A.01.01 page 72."
	::={saHpiEntry 18}


saHpiClearEvents OBJECT-TYPE
	SYNTAX		RowStatus
	MAX-ACCESS	read-write
	STATUS		current
	DESCRIPTION
	"Erase all of the system events for this particular
	resource. The saHpiSystemEventsLogTable will be affected."
	::= {saHpiEntry 19}

saHpiEventLogTime	OBJECT-TYPE
	SYNTAX		HpiTimeStamp
	MAX-ACCESS	read-write
	STATUS		current
	DESCRIPTION
	"This object retrieves (and sets) the current time from the 
	event log's (for the resource) own time clock. The value of 
	this clock is used to timestamp log entries written into the log.

	If the implementation cannot supply an absolute time value, then it may
	supply a time relative to some system-defined epoch, such as system
	boot. If the time value is less than or equal to
	SAHPI_TIME_MAX_RELATIVE(0x0C00000000000000LL), but not 
	SAHPI_TIME_UNSPECIFIED(0x8000000000000000LL), then it is
	relative; if it is greater than 
	SAHPI_TIME_MAX_RELATIVE(0x0C00000000000000LL), then it is
        absolute. The value SAHPI_TIME_UNSPECIFIED(0x8000000000000000LL)
	 indicates that the time is not set, or cannot be determined.
	"
	::= {saHpiEntry 20}

saHpiEventLogState OBJECT-TYPE
	SYNTAX	INTEGER {
			undefined(0),
			enable(1),
			disable(2)
		}
	MAX-ACCESS read-write
	STATUS	current
	DESCRIPTION 
	"The object enables system management software to get (and
	set) the event log state. If the event log is disable(2), 
	no events generated within the HPI implemention will be 
	added to the event log.
  
	When the event log is enable(1), events may be automatically 
	added to the event log as they are generated in a resource  
	or a domain.

	Typically, the HPI implementation will provide an appropriate 
	default value for this parameter, which may vary by resource. 
	This object is provided so that management software can 
	override the default value, if desired."
	::= {saHpiEntry 21}	
	
-- /*******************************************************************************
-- ********************************************************************************
-- **********                                                            **********
-- **********                        Events, Part 2                      **********
-- **********                                                            **********
-- ********************************************************************************
-- *******************************************************************************/
--

hpiEvents	OBJECT IDENTIFIER ::= { hpi 2 }

events		OBJECT IDENTIFIER ::= { hpiEvents 1 }

saHpiEventCount OBJECT-TYPE
	SYNTAX		Counter32
	MAX-ACCESS	read-only
	STATUS		current
	DESCRIPTION	"The number of events present on this system."
	::= {events 1}

saHpiEventTable OBJECT-TYPE
	SYNTAX		SEQUENCE OF SaHpiEventEntry
	MAX-ACCESS	not-accessible
	STATUS		current
	DESCRIPTION	"Event table. "
	::= {events 2}

saHpiEventEntry OBJECT-TYPE
	SYNTAX		SaHpiEventEntry
	MAX-ACCESS	not-accessible
	STATUS		current
	DESCRIPTION "
 Sensor events may contain optional data items passed and stored with the
 event. If these optional data items are present, they will be included with
 the event data returned in response to a SaHpiEventGet() or
 SaHpiEventLogEntryGet() function call. Also, the optional data items may be
 included with the event data passed to the SaHpiEventLogEntryAdd() function.

 Specific implementations of HPI may have restrictions on how much data may
 be passed to SaHpiEventLogEntryAdd(). These restrictions should be documented
 by the provider of the HPI interface."
	INDEX	{ saHpiDomainID, saHpiResourceID ,saHpiEventIndex}
	::= {saHpiEventTable 1}

SaHpiEventEntry ::= SEQUENCE {
	saHpiEventIndex		Unsigned32,
	saHpiEventType		INTEGER,
	saHpiEventTimestamp	HpiTimeStamp,

	saHpiEventSeverity	INTEGER,
	saHpiEventSensorNum	Unsigned32,
	saHpiEventSensorType	INTEGER,
	saHpiEventSensorCategory	INTEGER,
	saHpiEventSensorAssertion	TruthValue,

        saHpiEventSensorState 		OCTET STRING,

	saHpiEventSensorOptionalData	Unsigned32,

	saHpiEventSensorTriggerReadingType	      INTEGER,
	saHpiEventSensorTriggerReadingRaw	      Unsigned32,
	saHpiEventSensorTriggerReadingInterpreted   OCTET STRING,
	saHpiEventSensorTriggerReadingEventStateFlag INTEGER,
	saHpiEventSensorTriggerReadingEventState    OCTET STRING,

	saHpiEventSensorTriggerThresholdType	      INTEGER,
	saHpiEventSensorTriggerThresholdRaw	      Unsigned32,
	saHpiEventSensorTriggerThresholdInterpreted OCTET STRING,
	saHpiEventSensorTriggerThresholdEventStateFlag  INTEGER,
	saHpiEventSensorTriggerThresholdEventState  OCTET STRING,

	saHpiEventSensorPreviousState		OCTET STRING,
	saHpiEventSensorOem			Unsigned32,
	saHpiEventSensorSpecific	Unsigned32,

	saHpiEventHotSwapState		INTEGER,
	saHpiEventPreviousHotSwapState	INTEGER,

	saHpiEventWatchdogNum		Unsigned32,
	saHpiEventWatchdogAction	INTEGER,
	saHpiEventWatchdogPreTimerAction INTEGER,
	saHpiEventWatchdogUse		INTEGER,

	saHpiEventOemManufacturerIdT	Unsigned32,
	saHpiEventOemEventData		OCTET STRING,

	saHpiEventUserEventData		OCTET STRING,

	saHpiEventDelete		RowStatus
	}

saHpiEventIndex OBJECT-TYPE
        SYNTAX          Unsigned32
        MAX-ACCESS      read-only
        STATUS          current
        DESCRIPTION     "Index of the event. "
        ::= {saHpiEventEntry 1}

saHpiEventType OBJECT-TYPE
        SYNTAX          INTEGER {
				undefined(0),
				sensor(1),
				hotswap(2),
				watchdog(3),
				oem(4),
				user(5)
			}
        MAX-ACCESS      read-only
        STATUS          current
        DESCRIPTION     "
	The type of event.

	Note:
	User events may be used for storing custom events created by 
	the application  middleware; eg. when injecting events into 
	the event log using SaHpiEventLogEntryAdd(). 
	
	Note: The enumerated named have +1 added as opposed to the SA HPI 
	spec for the same constants.  "
        ::= {saHpiEventEntry 2}

saHpiEventTimestamp OBJECT-TYPE
        SYNTAX          HpiTimeStamp 
        MAX-ACCESS      read-only
        STATUS          current
	DESCRIPTION	"The time of the event.
	Time in the format of a 64-bit unsigned integer.
	If the implementation cannot supply an absolute timestamp, then it may
	supply a timestamp relative to some system-defined epoch, such as 
	system boot. The value SAHPI_TIME_UNSPECIFIED indicates that the 
	time of the update cannot be determined.

	Otherwise, If the value is less than or equal to 
	SAHPI_TIME_MAX_RELATIVE, then it is relative; 
	if it is greater than SAHPI_TIME_MAX_RELATIVE, then it is absolute.

	Unspecified or unknown time  is:
			 SAHPI_TIME_UNSPECIFIED     0x8000000000000000
			
	Maximum time that can be specified as relative:
			 SAHPI_TIME_MAX_RELATIVE    0x0C00000000000000 
			 
	Note: The same functionality - when the table is changed - 
	is available via notifications."
        ::= {saHpiEventEntry 3}

saHpiEventSeverity OBJECT-TYPE
        SYNTAX          INTEGER{
				undefined (0),
				critical(1),
				major(2),
				minor(3),
				informational(4),
				ok(5),
				debug(241)
			}
        MAX-ACCESS      read-only
        STATUS          current
        DESCRIPTION     "Severity of event. 
	Note: The enumerated named have +1 added as opposed to the 
	SA HPI spec for the same constants.  "
        ::= {saHpiEventEntry 4}


saHpiEventSensorNum OBJECT-TYPE
        SYNTAX          Unsigned32
        MAX-ACCESS      read-only
        STATUS          current
        DESCRIPTION     "The sensor number-index. 

	Note: This object is only valid if saHpiEventType = sensor(1)"
        ::= {saHpiEventEntry 5}

saHpiEventSensorType OBJECT-TYPE
        SYNTAX          INTEGER {
				undefined(0),
				temperature (2),
				voltage (3),
				current (4),
				fan (5),
				physicalSecurity (6),
				platformViolation (7),
				processor (8),
				powerSupply (9),
				powerUnit (10),
				coolingDevice (11),
				otherUnitsBasedSensor (12),
				memory (13),
				driveSlot (14),
				postMemoryResize (15),
				systemFwProgress (16),
				eventLoggingDisabled (17),
				reserved1 (18),
				systemEvent (19),
				criticalInterrupt (20),
				button (21),
				moduleBoard (22),
				microcontrollerCoprocessor (23),
				addinCard (24),
				chassis (25),
				chipSet (26),
				otherFru (27),
				cableInterconnect (28),
				terminator (29),
				systemBootInitiated (30),
				bootError (31),
				osBoot (32),
				osCriticalStop (33),
				slotConnector (34),
				systemAcpiPowerState (35),
				reserved2 (36),
				platformAlert (37),
				entityPresence (38),
				monitorAsicIc (39),
				lan (40),
				managementSubsystemHealth (41),
				battery (42),
				operational (161),
				oemSensor (193)
			}
        MAX-ACCESS      read-only
        STATUS          current
        DESCRIPTION     "General Sensor Type

	Note: This object is only valid if saHpiEventType = sensor(1)"
        ::= {saHpiEventEntry 6}

saHpiEventSensorCategory OBJECT-TYPE
        SYNTAX          INTEGER {
				unspecified (0),
				threshold (2),
				usage (3),
				state (4),
				predFail (5),
				limit (6),
				performance (7),
				severity (8),
				presence (9),
				enable (10),
				availability (11),
				redundancy (12),
				user (127),
				generic (128)
			}
        MAX-ACCESS      read-only
        STATUS          current
        DESCRIPTION     " 
	Sensor events contain an event category and event state. Depending on the
 	event category, the event states take on different meanings for events
 	generated by specific sensors.

 	The generic(127) category can be used for discrete sensors which have
 	state meanings other than those identified with other event categories."
        ::= {saHpiEventEntry 7}

saHpiEventSensorAssertion OBJECT-TYPE
        SYNTAX          TruthValue
        MAX-ACCESS      read-only
        STATUS          current
        DESCRIPTION     "TRUE = Event State asserted.  FALSE = deasserted "
        ::= {saHpiEventEntry 8}

saHpiEventSensorState OBJECT-TYPE
	SYNTAX		OCTET STRING
	MAX-ACCESS	read-only
	STATUS		current
	DESCRIPTION	"

	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	::= {saHpiEventEntry 9}	

saHpiEventSensorOptionalData OBJECT-TYPE
        SYNTAX          Unsigned32(1..16)
        MAX-ACCESS      read-only
        STATUS          current
        DESCRIPTION     "Sensor Optional Data
			
	Sensor events may contain optional data items passed and stored with the 
	 event. If these optional data items are present, they will be included with 
	 the event data.

	The bit-flags for data is:

 	TRIGGER_READING   0x01
 	TRIGGER_THRESHOLD 0x02
 	OEM               0x04
 	PREVIOUS_STATE    0x08
 	SENSOR_SPECIFIC   0x10 " 
        ::= {saHpiEventEntry 10}


saHpiEventSensorTriggerReadingType OBJECT-TYPE
        SYNTAX          INTEGER {
				undefined(0),

				raw(2),
				interpreted(3),
				eventState(5),

				rawAndInterpreted(4),
				rawAndEventState(6),
				rawAndInterpretedAndEventState(8),

				interpretedAndEventState(7)
			}
        MAX-ACCESS      read-only
        STATUS          current
        DESCRIPTION     "
	Each sensor may support one or more of raw, 
	interpreted, or event status representations of the sensor data. 	
	For analog sensors the raw value is the raw value from the 
	sensor (such as ticks per fan blade) and the interpreted 
	value is the raw value converted in to a usable format 
	(such as RPM). The interpreted value can be calculated by 
	the HPI implementation using the sensor factors or by 
	another OEM means.  "
        ::= {saHpiEventEntry 11}

saHpiEventSensorTriggerReadingRaw OBJECT-TYPE
        SYNTAX          Unsigned32
        MAX-ACCESS      read-only
        STATUS          current
        DESCRIPTION     "
	If saHpiEventTriggerReadingType = raw(1) then this object
	contains the raw value of the sensor as unsigned 32-bit integer"
	::= {saHpiEventEntry 12}


saHpiEventSensorTriggerReadingInterpreted OBJECT-TYPE
        SYNTAX          OCTET STRING(SIZE(1..32)) 
        MAX-ACCESS      read-only
        STATUS          current
        DESCRIPTION     "
	If saHpiEventTriggerReadingType = interpreted(2) then this object
	contains the Value of interpreted sensor reading.  "
	
	::={saHpiEventEntry 13}


saHpiEventSensorTriggerReadingEventStateFlag OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION     "
	If saHpiEventTriggerReadingType = eventState(3) then this object
	contains the outstanding sensor event states.
	The sensor status structure is used to determine if sensor 
	scanning is enabled and if events are enabled. If events 
	are enabled, the structure will have valid data for the 
	outstanding sensor event states.  "
        ::= {saHpiEventEntry 14}

saHpiEventSensorTriggerReadingEventState OBJECT-TYPE
	SYNTAX		OCTET STRING
	MAX-ACCESS	read-only
	STATUS		current
	DESCRIPTION	"
	If saHpiEventTriggerReadingType = eventState(3) then this object
	contains the outstanding sensor event states.
	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiEventEntry 15}

saHpiEventSensorTriggerThresholdType OBJECT-TYPE
        SYNTAX          INTEGER {
				undefined(0),

				raw(2),
				interpreted(3),
				eventState(5),

				rawAndInterpreted(4),
				rawAndEventState(6),
				rawAndInterpretedAndEventState(8),

				interpretedAndEventState(7)
			}
        MAX-ACCESS      read-only
        STATUS          current
        DESCRIPTION     "
	Each sensor may support one or more of raw, 
	interpreted, or event status representations of the sensor data. 	
	For analog sensors the raw value is the raw value from the 
	sensor (such as ticks per fan blade) and the interpreted 
	value is the raw value converted in to a usable format 
	(such as RPM). The interpreted value can be calculated by 
	the HPI implementation using the sensor factors or by 
	another OEM means.  "
        ::= {saHpiEventEntry 16}

saHpiEventSensorTriggerThresholdRaw OBJECT-TYPE
        SYNTAX          Unsigned32
        MAX-ACCESS      read-only
        STATUS          current
        DESCRIPTION     "
	If saHpiEventTriggerThresholdType = raw(1) then this object
	contains the raw value of the sensor as unsigned 32-bit integer"
	::= {saHpiEventEntry 17}

saHpiEventSensorTriggerThresholdInterpreted OBJECT-TYPE
        SYNTAX          OCTET STRING(SIZE(1..32)) 
        MAX-ACCESS      read-only
        STATUS          current
        DESCRIPTION     "
	If saHpiEventTriggerThresholdType = interpreted(2) then this object
	contains the Value of interpreted sensor reading. " 
	::={saHpiEventEntry 18}


saHpiEventSensorTriggerThresholdEventStateFlag OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION     "
	If saHpiEventTriggerThresholdType = eventState(3) then this object
	contains the outstanding sensor event states. 

	The sensor status structure is used to determine if sensor 
	scanning is enabled and if events are enabled. If events 
	are enabled, the structure will have valid data for the 
	outstanding sensor event states.  "
        ::= {saHpiEventEntry 19}

saHpiEventSensorTriggerThresholdEventState OBJECT-TYPE
        SYNTAX          OCTET STRING
        MAX-ACCESS      read-only
        STATUS          current
        DESCRIPTION     "
	If saHpiEventTriggerThresholdType = eventState(3) then this object
	contains the outstanding sensor event states. 

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	::= {saHpiEventEntry 20}

saHpiEventSensorPreviousState OBJECT-TYPE
	SYNTAX		OCTET STRING
	MAX-ACCESS	read-only
	STATUS		current
	DESCRIPTION	"
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	::= {saHpiEventEntry 21}

saHpiEventSensorOem OBJECT-TYPE
        SYNTAX          Unsigned32
        MAX-ACCESS      read-only
        STATUS          current
        DESCRIPTION     "Sensor OEM event information "
        ::= {saHpiEventEntry 22}

saHpiEventSensorSpecific OBJECT-TYPE
        SYNTAX          Unsigned32
        MAX-ACCESS      read-only
        STATUS          current
        DESCRIPTION     "Sensor specific information "
        ::= {saHpiEventEntry 23}


saHpiEventHotSwapState OBJECT-TYPE
        SYNTAX          INTEGER {
				undefined(0),
				inactive (1),
				insertionPending (2),
				activeHealthy (3),
				activeUnhealthy (4),
				extractionPending (5),
				notPresent (6)
			}
        MAX-ACCESS      read-only
        STATUS          current
        DESCRIPTION     "Current state of the hot-swap device."
        ::= {saHpiEventEntry 24}

saHpiEventPreviousHotSwapState OBJECT-TYPE
        SYNTAX           INTEGER{
				undefined(0),
				inactive (1),
				insertionPending (2),
				activeHealthy (3),
				activeUnhealthy (4),
				extractionPending (5),
				notPresent (6)
			}
        MAX-ACCESS      read-only
        STATUS          current
        DESCRIPTION     "Previous state of the hot-swap device. "
        ::= {saHpiEventEntry 25}

saHpiEventWatchdogNum OBJECT-TYPE
        SYNTAX          Unsigned32
        MAX-ACCESS      read-only
        STATUS          current
        DESCRIPTION     "The Watchdog number. "
        ::= {saHpiEventEntry 26}

saHpiEventWatchdogAction OBJECT-TYPE
        SYNTAX          INTEGER{ 
				undefined(0),
				noAction (1),
				reset (2),
				powerDown (3),
				powerCycle (4),
				timerInt (9)
			}
        MAX-ACCESS      read-only
        STATUS          current
        DESCRIPTION     "
	These enumerations represent the possible actions to be taken upon watchdog
 	timer timeout and the events that are generated for watchdog actions. "
        ::= {saHpiEventEntry 27}

saHpiEventWatchdogPreTimerAction OBJECT-TYPE
        SYNTAX          INTEGER{
				undefined(0),
				none (1),
				smi (2),
				nmi (3),
				messageInterrupt (4),
				oem (16)
			}
        MAX-ACCESS      read-only
        STATUS          current
        DESCRIPTION     " These enumerations represent the possible types of interrupts that may be
 			triggered by a watchdog pre-timer event. The actual meaning of these
 			operations may differ depending on the hardware architecture. "
        ::= {saHpiEventEntry 28}

saHpiEventWatchdogUse OBJECT-TYPE
        SYNTAX          INTEGER {
				undefined(0),
				none (1),
				biosFrb2 (2),
				biosPost (3),
				osLoad (4),
				smsOs (5),
				oem (6),
				unspecified (16)
			}
        MAX-ACCESS      read-only
        STATUS          current
        DESCRIPTION     "Watchdog Timer Use 
			
			 These enumerations represent the possible watchdog users that may have caused 
			 the watchdog to expire. For instance, if watchdog is being used during power 
			 on self test (POST), and it expires, the SAHPI_WTU_BIOS_POST expiration type 
			 will be set. Most specific uses for Watchdog timer by users of HPI should 
			 indicate SAHPI_WTU_SMS_OS  if the use is to provide an OS-healthy heartbeat, 
			 or SAHPI_WTU_OEM if it is used for some other purpose."
			
        ::= {saHpiEventEntry 29}

saHpiEventOemManufacturerIdT OBJECT-TYPE
        SYNTAX          Unsigned32
        MAX-ACCESS      read-only
        STATUS          current
        DESCRIPTION     " 
			 Identifier for the manufacturer 
			
			 This is the IANA-assigned private enterprise number for the
			 manufacturer of the resource or FRU, or of the manufacturer
			 defining an OEM control or event type. A list of current
			 IANA-assigned private enterprise numbers may be obtained at
			
			     http:www.iana.orgassignmentsenterprise-numbers
			
			 If a manufacturer does not currently have an assigned number, one
			 may be obtained by following the instructions located at
			
			     http:www.iana.orgcgi-binenterprise.pl
			Its SAHPI_MANUFACTURER_ID_UNSPECIFIED(0) if not known.
			"
        ::= {saHpiEventEntry 30}

saHpiEventOemEventData OBJECT-TYPE
        SYNTAX          OCTET STRING(SIZE(0..32))
        MAX-ACCESS      read-only
        STATUS          current
        DESCRIPTION     "Events provided by OEM."
        ::= {saHpiEventEntry 31}


saHpiEventUserEventData OBJECT-TYPE
        SYNTAX          OCTET STRING(SIZE(0..32))
        MAX-ACCESS      read-only
        STATUS          current
        DESCRIPTION     "User events may be used for storing custom events 
			created by the application  middleware;
			eg. when injecting events into the event log using SaHpiEventLogEntryAdd().  "
        ::= {saHpiEventEntry 32}

saHpiEventDelete OBJECT-TYPE
	SYNTAX		RowStatus
	MAX-ACCESS	read-write
	STATUS		current
	DESCRIPTION	
	"Set this to destory(6) or notInService(2) to delete this entry."
	::= {saHpiEventEntry 33}

--/*******************************************************************************
-- * ********************************************************************************
-- * ********** ********** ********** System Event Log ********** **********
-- * **********
-- * ********************************************************************************
-- * *******************************************************************************/

systemEvents	OBJECT IDENTIFIER ::= { hpiEvents 2}

saHpiSystemEventLogEntries OBJECT-TYPE
	SYNTAX		Unsigned32
	MAX-ACCESS	read-only
	STATUS		current
	DESCRIPTION	" The Entries entry denotes the number of active entries contained in the log."
	::= {systemEvents 1}

saHpiSystemEventLogSize OBJECT-TYPE
	SYNTAX		Unsigned32
	MAX-ACCESS	read-only
	STATUS		current
	DESCRIPTION	" The Size entry denotes the total number of entries the log is able to hold."
	::= {systemEvents 2}

saHpiSystemEventLogUpdateTimestamp OBJECT-TYPE
	SYNTAX		HpiTimeStamp
	MAX-ACCESS	read-only
	STATUS		current
	DESCRIPTION	"The UpdateTimestamp entry denotes the timestamp of the last addition,
   			deletion or log clear operation.

				This time is set any time the table is
                                     changed. If the implementation cannot
                                     supply an absolute timestamp, then it may
                                     supply a timestamp relative to some system-
                                     defined epoch, such as system boot. The
                                     value SAHPI_TIME_UNSPECIFIED indicates that
                                     the time of the update cannot be determined.
                                     Otherwise, If the value is less than or
                                     equal to SAHPI_TIME_MAX_RELATIVE, then it
                                     is relative; if it is greater than
                                     SAHPI_TIME_MAX_RELATIVE, then it is absolute.


			 Unspecified or unknown time  is:
			 SAHPI_TIME_UNSPECIFIED     0x8000000000000000
			
			 Maximum time that can be specified as relative 
			 SAHPI_TIME_MAX_RELATIVE    0x0C00000000000000 "
	::= {systemEvents 3}

saHpiSystemEventLogCurrentTime OBJECT-TYPE
	SYNTAX		HpiTimeStamp
	MAX-ACCESS	read-only
	STATUS		current
	DESCRIPTION	"The CurrentTime entry denotes the log's idea of the current time; i.e the
   			timestamp that would be placed on an entry if it was added now.
				This time is set any time the table is
                                     changed. If the implementation cannot
                                     supply an absolute timestamp, then it may
                                     supply a timestamp relative to some system-
                                     defined epoch, such as system boot. The
                                     value SAHPI_TIME_UNSPECIFIED indicates that
                                     the time of the update cannot be determined.
                                     Otherwise, If the value is less than or
                                     equal to SAHPI_TIME_MAX_RELATIVE, then it
                                     is relative; if it is greater than
                                     SAHPI_TIME_MAX_RELATIVE, then it is absolute.


			 Unspecified or unknown time  is:
			 SAHPI_TIME_UNSPECIFIED     0x8000000000000000
			
			 Maximum time that can be specified as relative 
			 SAHPI_TIME_MAX_RELATIVE    0x0C00000000000000 "
	::= {systemEvents 4}

saHpiSystemEventLogEnabled OBJECT-TYPE
	SYNTAX		TruthValue
	MAX-ACCESS	read-only
	STATUS		current
	DESCRIPTION	"The Enabled entry indicates whether the log is enabled. If the event log
			   is 'disabled' no events generated within the HPI implementation will be
			   added to the event log. Events may still be added to the event log with
			   the SaHpiEventLogEntryAdd() function. When the event log is 'enabled'
			   events may be automatically added to the event log as they are generated
			   in a resource or a domain, however, it is implementation-specific which
			   events are automatically added to any event log.  "
	::= {systemEvents 5}

saHpiSystemEventLogOverflowFlag OBJECT-TYPE
	SYNTAX		TruthValue 	
	MAX-ACCESS	read-only
	STATUS		current
	DESCRIPTION	" The OverflowFlag entry indicates the log has overflowed. Events have been 
			   dropped or overwritten due to a table overflow. "
	::= {systemEvents 6}

saHpiSystemEventLogOverflowAction OBJECT-TYPE
	SYNTAX		INTEGER{
				undefined(0),
				drop(1),
				wrap(2),
				writeLast(3)
			}
	MAX-ACCESS	read-only
	STATUS		current
	DESCRIPTION	"The OverflowAction entry indicates the behavior of the SEL when an overflow 
			   occurs. 

			    SAHPI_SEL_OVERFLOW_DROP,         New entries are dropped when log is full
			    SAHPI_SEL_OVERFLOW_WRAP,         Log wraps when log is full 
			    SAHPI_SEL_OVERFLOW_WRITELAST     Last entry overwritten when log is full "
	::= {systemEvents 7}

saHpiSystemEventLogDeleteEntrySupported OBJECT-TYPE
	SYNTAX		TruthValue
	MAX-ACCESS	read-only
	STATUS		current
	DESCRIPTION	"The DeleteEntrySupported indicates whether the delete command is supported for 
			   event log entries. Note that clearing an entire log is valid even if this
			   flag is not set."
	::= {systemEvents 8}

saHpiSystemEventLogTable OBJECT-TYPE
        SYNTAX          SEQUENCE OF SaHpiSystemEventLogEntry
        MAX-ACCESS      not-accessible
        STATUS          current
        DESCRIPTION     "A table definining System Event Log records."
        ::= {systemEvents 9}


saHpiSystemEventLogEntry OBJECT-TYPE
        SYNTAX          SaHpiSystemEventLogEntry
        MAX-ACCESS      not-accessible
        STATUS          current
        DESCRIPTION 	"This section defines the types associated with the SEL."
        INDEX   { saHpiDomainID, saHpiResourceID  ,saHpiSystemEventLogIndex }

        ::= {saHpiSystemEventLogTable 1}
                                                 
SaHpiSystemEventLogEntry ::= SEQUENCE {
	saHpiSystemEventLogIndex	Unsigned32,
	saHpiSystemEventLogAddedTimestamp	HpiTimeStamp,
	saHpiSystemEventLogType		INTEGER,
	saHpiSystemEventLogTimestamp	HpiTimeStamp,

	saHpiSystemEventLogSeverity	INTEGER,
	saHpiSystemEventLogSensorNum	Unsigned32,
	saHpiSystemEventLogSensorType	INTEGER,
	saHpiSystemEventLogSensorCategory	INTEGER,
	saHpiSystemEventLogSensorAssertion	TruthValue,

        saHpiSystemEventLogSensorState OCTET STRING,

	saHpiSystemEventLogSensorOptionalData	Unsigned32,

	saHpiSystemEventLogSensorTriggerReadingType	      INTEGER,
	saHpiSystemEventLogSensorTriggerReadingRaw	      Unsigned32,
	saHpiSystemEventLogSensorTriggerReadingInterpreted   OCTET STRING,
	saHpiSystemEventLogSensorTriggerReadingEventStateFlag   INTEGER, 
	saHpiSystemEventLogSensorTriggerReadingEventState    OCTET STRING,

	saHpiSystemEventLogSensorTriggerThresholdType	      INTEGER,
	saHpiSystemEventLogSensorTriggerThresholdRaw	      Unsigned32,
	saHpiSystemEventLogSensorTriggerThresholdInterpreted OCTET STRING,
	saHpiSystemEventLogSensorTriggerThresholdEventStateFlag  INTEGER,
	saHpiSystemEventLogSensorTriggerThresholdEventState  OCTET STRING,

	saHpiSystemEventLogSensorPreviousState		OCTET STRING,
	saHpiSystemEventLogSensorOem			Unsigned32,
	saHpiSystemEventLogSensorSpecific	Unsigned32,

	saHpiSystemEventLogHotSwapState		INTEGER,
	saHpiSystemEventLogPreviousHotSwapState	INTEGER,

	saHpiSystemEventLogWatchdogNum		Unsigned32,
	saHpiSystemEventLogWatchdogAction	INTEGER,
	saHpiSystemEventLogWatchdogPreTimerAction INTEGER,
	saHpiSystemEventLogWatchdogUse		INTEGER,

	saHpiSystemEventLogOemManufacturerIdT	Unsigned32,
	saHpiSystemEventLogOemEventData		OCTET STRING,

	saHpiSystemEventLogUserEventData		OCTET STRING,

	saHpiSystemEventLogDelete		RowStatus
	}

saHpiSystemEventLogIndex OBJECT-TYPE
        SYNTAX          Unsigned32
        MAX-ACCESS      read-only
        STATUS          current
        DESCRIPTION     "Entry ID for record

 			Reserved values for event log entry IDs

 			SAHPI_OLDEST_ENTRY    0x00000000
 			SAHPI_NEWEST_ENTRY    0xFFFFFFFF
 			SAHPI_NO_MORE_ENTRIES 0xFFFFFFFE
			"
        ::= {saHpiSystemEventLogEntry 1}

saHpiSystemEventLogAddedTimestamp OBJECT-TYPE
        SYNTAX          HpiTimeStamp
        MAX-ACCESS      read-only
        STATUS          current
	DESCRIPTION	"This time is set any time the table is
                                     changed. If the implementation cannot
                                     supply an absolute timestamp, then it may
                                     supply a timestamp relative to some system-
                                     defined epoch, such as system boot. The
                                     value SAHPI_TIME_UNSPECIFIED indicates that
                                     the time of the update cannot be determined.
                                     Otherwise, If the value is less than or
                                     equal to SAHPI_TIME_MAX_RELATIVE, then it
                                     is relative; if it is greater than
                                     SAHPI_TIME_MAX_RELATIVE, then it is absolute.


			 Unspecified or unknown time  is:
			 SAHPI_TIME_UNSPECIFIED     0x8000000000000000
			
			 Maximum time that can be specified as relative 
			 SAHPI_TIME_MAX_RELATIVE    0x0C00000000000000 "
        ::= {saHpiSystemEventLogEntry 2}

saHpiSystemEventLogType OBJECT-TYPE
        SYNTAX          INTEGER {
				undefined(0),
				sensor(1),
				hotswap(2),
				watchdog(3),
				oem(4),
				user(5)
			}
        MAX-ACCESS      read-only
        STATUS          current
        DESCRIPTION     "
	The type of event.

	Note:
	User events may be used for storing custom events created by 
	the application  middleware; eg. when injecting events into 
	the event log using SaHpiEventLogEntryAdd(). 
	
	Note: The enumerated named have +1 added as opposed to the SA HPI 
	spec for the same constants.  "
	::= {saHpiSystemEventLogEntry 3}

saHpiSystemEventLogTimestamp OBJECT-TYPE
        SYNTAX          HpiTimeStamp 
        MAX-ACCESS      read-only
        STATUS          current
	DESCRIPTION	"The time of the event.
	Time in the format of a 64-bit unsigned integer.
	If the implementation cannot supply an absolute timestamp, then it may
	supply a timestamp relative to some system-defined epoch, such as 
	system boot. The value SAHPI_TIME_UNSPECIFIED indicates that the 
	time of the update cannot be determined.

	Otherwise, If the value is less than or equal to 
	SAHPI_TIME_MAX_RELATIVE, then it is relative; 
	if it is greater than SAHPI_TIME_MAX_RELATIVE, then it is absolute.

	Unspecified or unknown time  is:
			 SAHPI_TIME_UNSPECIFIED     0x8000000000000000
			
	Maximum time that can be specified as relative:
			 SAHPI_TIME_MAX_RELATIVE    0x0C00000000000000 
			 
	Note: The same functionality - when the table is changed - 
	is available via notifications."
	::= {saHpiSystemEventLogEntry 4}

saHpiSystemEventLogSeverity OBJECT-TYPE
        SYNTAX          INTEGER{
				undefined (0),
				critical(1),
				major(2),
				minor(3),
				informational(4),
				ok(5),
				debug(241)
			}
        MAX-ACCESS      read-only
        STATUS          current
        DESCRIPTION     "Severity of event. 
	Note: The enumerated named have +1 added as opposed to the SA HPI 
	spec for the same constants.  "
	::= {saHpiSystemEventLogEntry 5}


saHpiSystemEventLogSensorNum OBJECT-TYPE
        SYNTAX          Unsigned32
        MAX-ACCESS      read-only
        STATUS          current
        DESCRIPTION     "The sensor number-index. 

	Note: This object is only valid if saHpiSystemEventLogType = sensor(1)"
	::= {saHpiSystemEventLogEntry 6}

saHpiSystemEventLogSensorType OBJECT-TYPE
        SYNTAX          INTEGER {
				undefined(0),
				temperature (2),
				voltage (3),
				current (4),
				fan (5),
				physicalSecurity (6),
				platformViolation (7),
				processor (8),
				powerSupply (9),
				powerUnit (10),
				coolingDevice (11),
				otherUnitsBasedSensor (12),
				memory (13),
				driveSlot (14),
				postMemoryResize (15),
				systemFwProgress (16),
				eventLoggingDisabled (17),
				reserved1 (18),
				systemEvent (19),
				criticalInterrupt (20),
				button (21),
				moduleBoard (22),
				microcontrollerCoprocessor (23),
				addinCard (24),
				chassis (25),
				chipSet (26),
				otherFru (27),
				cableInterconnect (28),
				terminator (29),
				systemBootInitiated (30),
				bootError (31),
				osBoot (32),
				osCriticalStop (33),
				slotConnector (34),
				systemAcpiPowerState (35),
				reserved2 (36),
				platformAlert (37),
				entityPresence (38),
				monitorAsicIc (39),
				lan (40),
				managementSubsystemHealth (41),
				battery (42),
				operational (161),
				oemSensor (193)
			}
        MAX-ACCESS      read-only
        STATUS          current
        DESCRIPTION     "General Sensor Type

	Note: This object is only valid if saHpiSystemEventLogType = sensor(1)"
	::= {saHpiSystemEventLogEntry 7}

saHpiSystemEventLogSensorCategory OBJECT-TYPE
        SYNTAX          INTEGER {
				unspecified (0),
				threshold (2),
				usage (3),
				state (4),
				predFail (5),
				limit (6),
				performance (7),
				severity (8),
				presence (9),
				enable (10),
				availability (11),
				redundancy (12),
				user (127),
				generic (128)
			}
        MAX-ACCESS      read-only
        STATUS          current
        DESCRIPTION     " 
	Sensor events contain an event category and event state. Depending on the
 	event category, the event states take on different meanings for events
 	generated by specific sensors.

 	The generic(127) category can be used for discrete sensors which have
 	state meanings other than those identified with other event categories."
	::= {saHpiSystemEventLogEntry 8}

saHpiSystemEventLogSensorAssertion OBJECT-TYPE
        SYNTAX          TruthValue
        MAX-ACCESS      read-only
        STATUS          current
        DESCRIPTION     "TRUE = Event State asserted.  FALSE = deasserted "
	::= {saHpiSystemEventLogEntry 9}

saHpiSystemEventLogSensorState OBJECT-TYPE
        SYNTAX          OCTET STRING
        MAX-ACCESS      read-only
        STATUS          current
        DESCRIPTION     "

	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	::= {saHpiSystemEventLogEntry 10}

saHpiSystemEventLogSensorOptionalData OBJECT-TYPE
        SYNTAX          Unsigned32(1..16)
        MAX-ACCESS      read-only
        STATUS          current
        DESCRIPTION     "Sensor Optional Data
			
	Sensor events may contain optional data items passed and stored with the 
	 event. If these optional data items are present, they will be included with 
	 the event data.

	The bit-flags for data is:

 	TRIGGER_READING   0x01
 	TRIGGER_THRESHOLD 0x02
 	OEM               0x04
 	PREVIOUS_STATE    0x08
 	SENSOR_SPECIFIC   0x10 " 
	::= {saHpiSystemEventLogEntry 11}

saHpiSystemEventLogSensorTriggerReadingType OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION     "
	Each sensor may support one or more of raw, 
	interpreted, or event status representations of the sensor data. 	
	For analog sensors the raw value is the raw value from the 
	sensor (such as ticks per fan blade) and the interpreted 
	value is the raw value converted in to a usable format 
	(such as RPM). The interpreted value can be calculated by 
	the HPI implementation using the sensor factors or by 
	another OEM means.  "
	::= {saHpiSystemEventLogEntry 12}

saHpiSystemEventLogSensorTriggerReadingRaw OBJECT-TYPE
        SYNTAX          Unsigned32
        MAX-ACCESS      read-only
        STATUS          current
        DESCRIPTION     "
	If saHpiSystemEventLogTriggerReadingType = raw(1) then this object
	contains the raw value of the sensor as unsigned 32-bit integer"
	::= {saHpiSystemEventLogEntry 13}


saHpiSystemEventLogSensorTriggerReadingInterpreted OBJECT-TYPE
        SYNTAX          OCTET STRING(SIZE(1..32)) 
        MAX-ACCESS      read-only
        STATUS          current
        DESCRIPTION     "
	If saHpiSystemEventLogTriggerReadingType = interpreted(2) then this object
	contains the Value of interpreted sensor reading.  "
	::= {saHpiSystemEventLogEntry 14}

saHpiSystemEventLogSensorTriggerReadingEventStateFlag OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)				
			}
        MAX-ACCESS      read-only
        STATUS          current
        DESCRIPTION     "
	If saHpiSystemEventLogTriggerReadingType = eventState(3) then this object
	contains the outstanding sensor event states.
	The sensor status structure is used to determine if sensor 
	scanning is enabled and if events are enabled. If events 
	are enabled, the structure will have valid data for the 
	outstanding sensor event states.  "
	 ::= {saHpiSystemEventLogEntry 15}

saHpiSystemEventLogSensorTriggerReadingEventState OBJECT-TYPE
	SYNTAX		OCTET STRING
	MAX-ACCESS	read-only
	STATUS		current
	DESCRIPTION	"
	If saHpiSystemEventLogTriggerReadingType = eventState(3) then this object
	contains the outstanding sensor event states.
	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	 ::= {saHpiSystemEventLogEntry 16}

saHpiSystemEventLogSensorTriggerThresholdType OBJECT-TYPE
        SYNTAX         INTEGER {
				undefined(0),

				raw(2),
				interpreted(3),
				eventState(5),

				rawAndInterpreted(4),
				rawAndEventState(6),
				rawAndInterpretedAndEventState(8),

				interpretedAndEventState(7)
			}
        MAX-ACCESS      read-only
        STATUS          current
        DESCRIPTION     "
	Each sensor may support one or more of raw, 
	interpreted, or event status representations of the sensor data. 	
	For analog sensors the raw value is the raw value from the 
	sensor (such as ticks per fan blade) and the interpreted 
	value is the raw value converted in to a usable format 
	(such as RPM). The interpreted value can be calculated by 
	the HPI implementation using the sensor factors or by 
	another OEM means.  "
	 ::= {saHpiSystemEventLogEntry 17}

saHpiSystemEventLogSensorTriggerThresholdRaw OBJECT-TYPE
        SYNTAX          Unsigned32
        MAX-ACCESS      read-only
        STATUS          current
        DESCRIPTION     "
	If saHpiSystemEventLogTriggerThresholdType = raw(1) then this object
	contains the raw value of the sensor as unsigned 32-bit integer"
	 ::= {saHpiSystemEventLogEntry 18}

saHpiSystemEventLogSensorTriggerThresholdInterpreted OBJECT-TYPE
        SYNTAX          OCTET STRING(SIZE(1..32)) 
        MAX-ACCESS      read-only
        STATUS          current
        DESCRIPTION     "
	If saHpiSystemEventLogTriggerThresholdType = interpreted(2) then this object
	contains the Value of interpreted sensor reading.  "
	 ::={saHpiSystemEventLogEntry 19}


saHpiSystemEventLogSensorTriggerThresholdEventStateFlag OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION     "
	If saHpiSystemEventLogTriggerThresholdType = eventState(3) then this object
	contains the outstanding sensor event states. 

	The sensor status structure is used to determine if sensor 
	scanning is enabled and if events are enabled. If events 
	are enabled, the structure will have valid data for the 
	outstanding sensor event states.  "
	 ::= {saHpiSystemEventLogEntry 20}
saHpiSystemEventLogSensorTriggerThresholdEventState OBJECT-TYPE
        SYNTAX          OCTET STRING
        MAX-ACCESS      read-only
        STATUS          current
        DESCRIPTION     "
	If saHpiSystemEventLogTriggerThresholdType = eventState(3) then this object
	contains the outstanding sensor event states. 

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	 ::= {saHpiSystemEventLogEntry 21}

saHpiSystemEventLogSensorPreviousState OBJECT-TYPE
	SYNTAX		OCTET STRING
	MAX-ACCESS	read-only
	STATUS		current
	DESCRIPTION	"
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
	 ::= {saHpiSystemEventLogEntry 22}

saHpiSystemEventLogSensorOem OBJECT-TYPE
        SYNTAX          Unsigned32
        MAX-ACCESS      read-only
        STATUS          current
        DESCRIPTION     "Sensor OEM event information "
	 ::= {saHpiSystemEventLogEntry 23}

saHpiSystemEventLogSensorSpecific OBJECT-TYPE
        SYNTAX          Unsigned32
        MAX-ACCESS      read-only
        STATUS          current
        DESCRIPTION     "Sensor specific information "
	 ::= {saHpiSystemEventLogEntry 24}


saHpiSystemEventLogHotSwapState OBJECT-TYPE
        SYNTAX          INTEGER {
				undefined(0),
				inactive (1),
				insertionPending (2),
				activeHealthy (3),
				activeUnhealthy (4),
				extractionPending (5),
				notPresent (6)
			}
        MAX-ACCESS      read-only
        STATUS          current
        DESCRIPTION     "Current state of the hot-swap device."
	 ::= {saHpiSystemEventLogEntry 25}

saHpiSystemEventLogPreviousHotSwapState OBJECT-TYPE
        SYNTAX           INTEGER{
				undefined(0),
				inactive (1),
				insertionPending (2),
				activeHealthy (3),
				activeUnhealthy (4),
				extractionPending (5),
				notPresent (6)
			}
        MAX-ACCESS      read-only
        STATUS          current
        DESCRIPTION     "Previous state of the hot-swap device. "
	 ::= {saHpiSystemEventLogEntry 26}

saHpiSystemEventLogWatchdogNum OBJECT-TYPE
        SYNTAX          Unsigned32
        MAX-ACCESS      read-only
        STATUS          current
        DESCRIPTION     "The Watchdog number. "
	 ::= {saHpiSystemEventLogEntry 27}

saHpiSystemEventLogWatchdogAction OBJECT-TYPE
        SYNTAX          INTEGER{ 
				undefined(0),
				noAction (1),
				reset (2),
				powerDown (3),
				powerCycle (4),
				timerInt (9)
			}
        MAX-ACCESS      read-only
        STATUS          current
        DESCRIPTION     "
	These enumerations represent the possible actions to be taken upon watchdog
 	timer timeout and the events that are generated for watchdog actions. "
	 ::= {saHpiSystemEventLogEntry 28}

saHpiSystemEventLogWatchdogPreTimerAction OBJECT-TYPE
        SYNTAX          INTEGER{
				undefined(0),
				none (1),
				smi (2),
				nmi (3),
				messageInterrupt (4),
				oem (16)
			}
        MAX-ACCESS      read-only
        STATUS          current
        DESCRIPTION     " These enumerations represent the possible types of interrupts that may be
 			triggered by a watchdog pre-timer event. The actual meaning of these
 			operations may differ depending on the hardware architecture. "
	 ::= {saHpiSystemEventLogEntry 29}

saHpiSystemEventLogWatchdogUse OBJECT-TYPE
        SYNTAX          INTEGER {
				undefined(0),
				none (1),
				biosFrb2 (2),
				biosPost (3),
				osLoad (4),
				smsOs (5),
				oem (6),
				unspecified (16)
			}
        MAX-ACCESS      read-only
        STATUS          current
        DESCRIPTION     "Watchdog Timer Use 
			
			 These enumerations represent the possible watchdog users that may have caused 
			 the watchdog to expire. For instance, if watchdog is being used during power 
			 on self test (POST), and it expires, the SAHPI_WTU_BIOS_POST expiration type 
			 will be set. Most specific uses for Watchdog timer by users of HPI should 
			 indicate SAHPI_WTU_SMS_OS  if the use is to provide an OS-healthy heartbeat, 
			 or SAHPI_WTU_OEM if it is used for some other purpose."
			
	 ::= {saHpiSystemEventLogEntry 30}

saHpiSystemEventLogOemManufacturerIdT OBJECT-TYPE
        SYNTAX          Unsigned32
        MAX-ACCESS      read-only
        STATUS          current
        DESCRIPTION     " 
			 Identifier for the manufacturer 
			
			 This is the IANA-assigned private enterprise number for the
			 manufacturer of the resource or FRU, or of the manufacturer
			 defining an OEM control or event type. A list of current
			 IANA-assigned private enterprise numbers may be obtained at
			
			     http:www.iana.orgassignmentsenterprise-numbers
			
			 If a manufacturer does not currently have an assigned number, one
			 may be obtained by following the instructions located at
			
			     http:www.iana.orgcgi-binenterprise.pl
			Its SAHPI_MANUFACTURER_ID_UNSPECIFIED(0) if not known.
			"
	 ::= {saHpiSystemEventLogEntry 31}

saHpiSystemEventLogOemEventData OBJECT-TYPE
        SYNTAX          OCTET STRING(SIZE(0..32))
        MAX-ACCESS      read-only
        STATUS          current
        DESCRIPTION     "Events provided by OEM."
	 ::= {saHpiSystemEventLogEntry 32}


saHpiSystemEventLogUserEventData OBJECT-TYPE
        SYNTAX          OCTET STRING(SIZE(0..32))
        MAX-ACCESS      read-only
        STATUS          current
        DESCRIPTION     "User events may be used for storing custom events 
			created by the application  middleware;
			eg. when injecting events into the event log using SaHpiSystemEventLogLogEntryAdd().  "
	 ::= {saHpiSystemEventLogEntry 33}

saHpiSystemEventLogDelete OBJECT-TYPE
	SYNTAX		RowStatus
	MAX-ACCESS	read-write
	STATUS		current
	DESCRIPTION	
	"Set this to destory(6) or notInService(2) to delete this entry."
	::= {saHpiSystemEventLogEntry 34}

--/*******************************************************************************
-- * ********************************************************************************
-- * ********** ********** ********** Hot Swap table ********** **********
-- * **********
-- * ********************************************************************************
-- * *******************************************************************************/

saHpiHotSwapTable OBJECT-TYPE
    SYNTAX SEQUENCE OF SaHpiHotSwapEntry
    MAX-ACCESS not-accessible
    STATUS current
    DESCRIPTION
        "This table represents management attributes common to all hot swappable 
         entities in the managed platform.  The entries in this table are 
         straight from the HPI spec.  This table builds upon information present 
         in the Entity Table."
    ::= { hpiResources 12 }


saHpiHotSwapEntry OBJECT-TYPE
    SYNTAX SaHpiHotSwapEntry
    MAX-ACCESS not-accessible
    STATUS current
    DESCRIPTION
        "An entry describing a particular hot swappable entity."
    INDEX { saHpiDomainID, saHpiResourceID }
    ::= { saHpiHotSwapTable 1 }


SaHpiHotSwapEntry ::= SEQUENCE {
    saHpiHotSwapIndicator      INTEGER,
    saHpiHotSwapPowerState     INTEGER,
    saHpiHotSwapResetState     INTEGER,
    saHpiHotSwapState          INTEGER,
    saHpiHotSwapPreviousState  INTEGER,
    saHpiHotSwapEventSeverity  INTEGER,
    saHpiHotSwapInsertTimeout  Unsigned32,
    saHpiHotSwapExtractTimeout Unsigned32,
    saHpiHotSwapActionRequest  INTEGER,
    saHpiHotSwapRTP	       RowPointer }


saHpiHotSwapIndicator OBJECT-TYPE
    SYNTAX INTEGER {
    		undefined(0),
            off(1),
            on(2) }
    MAX-ACCESS read-create
    STATUS current
    DESCRIPTION
        "The indicator (typically an LED) indicating that an entity is ready to
                  be removed."
    REFERENCE 
        "Derived from typedef in the SAI-HPI-A.01.01 page 100."
    ::= { saHpiHotSwapEntry 1 }


saHpiHotSwapPowerState OBJECT-TYPE
    SYNTAX INTEGER {
    		undefined(0),
            off(1),
            on(2),
            cycle(3) }
    MAX-ACCESS read-create
    STATUS current
    DESCRIPTION
        "Indicates the power state of the entity."
    REFERENCE 
        "Derived from typedef in the SAI-HPI-A.01.01 page 100."
    ::= { saHpiHotSwapEntry 2 }


saHpiHotSwapResetState OBJECT-TYPE
    SYNTAX INTEGER {
    		undefined(0),
            coldReset(1),
            warmReset(2),
            resetAssert(3),
            resetDeassert(4) }
    MAX-ACCESS read-create
    STATUS current
    DESCRIPTION
        "coldReset(write-only): Executes a cold reset on entity.

         warmReset(write-only): Executes a warm reset on entity.

         resetAssert: When written, assert entity's reset line.  When read, 
                      indicates entity's reset line is asserted.

         resetDeassert: When written, deassert entity's reset line.  When read, 
                        indicates entity's reset line is deasserted."
    REFERENCE 
        "Derived from actions defined for function prototypes in the 
         SAI-HPI-A.02.01 pages 73, 74."
    ::= { saHpiHotSwapEntry 3 }


saHpiHotSwapState OBJECT-TYPE
    SYNTAX INTEGER {
    		undefined(0),
            inactive(1),
            insertionPending(2),
            activeHealthy(3),
            activeUnhealthy(4),
            extractionPending(5),
            notPresent(6) }
    MAX-ACCESS read-only
    STATUS current
    DESCRIPTION
        "The hot swap state of the resource.

         inactive: Indicates the FRU is no longer active in the system, and that 
                   it has completed the extraction process.

         activeHealthy: Indicates the entity is now an active 
                        member of the domain.  After a FRU completes the 
                        hardware connection process, the associated entity 
                        enters the activeHealthy state if there are no faults 
                        present.  An entity will transition between 
                        activeHealthy and activeUnhealthy as fault conditions                  
                        are asserted or cleared on the FRU.

         activeUnHealthy: Indicates the entity is now an active 
                          member of the domain.  After a FRU completes the 
                          hardware connection process, the associated entity 
                          enters the activeUnhealthy state if there are faults 
                          present.  An entity will transition between 
                          activeHealthy and activeUnhealthy as fault conditions 
                          are asserted or cleared on the FRU.

         extrationPending: Indicates that the entity has requested extraction of 
                           the associated FRU.  Typically an entity enters this 
                           state when an ejector latch is opened or when a hot 
                           swap button is pressed.

         insertionPending: Indicates entity is transitioning from notPresent or 
                           inactive to an active state as a result of being 
                           physically inserted into the system.

         notPresent: The entity is not present in the system."
    REFERENCE 
        "Derived from states described in the SAI-HPI-A.01.01 pages 62, 63."
    ::= { saHpiHotSwapEntry 4 }

saHpiHotSwapPreviousState OBJECT-TYPE
    SYNTAX INTEGER {
    		undefined(0),
            inactive(1),
            insertionPending(2),
            activeHealthy(3),
            activeUnhealthy(4),
            extractionPending(5),
            notPresent(6) }
    MAX-ACCESS read-only
    STATUS current
    DESCRIPTION
        "The previous hot swap state of the resource.  See hotSwapState 
         description for explanation of states."
    REFERENCE 
        "Derived from states described in the SAI-HPI-A.01.01 pages 62, 63."
    ::= { saHpiHotSwapEntry 5 }

saHpiHotSwapEventSeverity OBJECT-TYPE
    SYNTAX INTEGER {
    		undefined(0),
            critical(1),
            major(2),
            minor(3),
            informational(4),
            ok(5),
            debug(241) }
    MAX-ACCESS read-only
    STATUS current
    DESCRIPTION
        "Event severity."
    REFERENCE 
        "Derived from typedef saHpiSeverityT described in the SAI-HPI-A.01.01 
         pages 100, 101."
    ::= { saHpiHotSwapEntry 6 }


saHpiHotSwapInsertTimeout OBJECT-TYPE
    SYNTAX Unsigned32
    MAX-ACCESS read-create
    STATUS current
    DESCRIPTION
        "Indicates how long to wait (ns) after receiving a FRU insertion 
         indication before the default auto-insertion policy is invoked."
    REFERENCE 
        "Derived from function prototypes in the SAI-HPI-A.01.01 pages 65, 66."
    ::= { saHpiHotSwapEntry 7 }


saHpiHotSwapExtractTimeout OBJECT-TYPE
    SYNTAX Unsigned32
    MAX-ACCESS read-create
    STATUS current
    DESCRIPTION
        "Indicates how long to wait (ns) after receiving a FRU extraction 
         indication before the default auto-extraction policy is invoked."
    REFERENCE 
        "Derived from function prototypes in the SAI-HPI-A.01.01 pages 67, 68."
    ::= { saHpiHotSwapEntry 8 }


saHpiHotSwapActionRequest OBJECT-TYPE
    SYNTAX INTEGER {
    		undefined(0),
            insertion(1),
            extraction(2) }
    MAX-ACCESS read-create
    STATUS current
    DESCRIPTION
        "This is set when the user wants to invoke either the auto-insertion or
         auto-extraction policy without waiting for a FRU insertion/extraction 
         first."
    REFERENCE 
        "Derived from function prototype in the SAI-HPI-A.01.01 page 69."
    ::= {saHpiHotSwapEntry 9}

saHpiHotSwapRTP	OBJECT-TYPE
	SYNTAX		RowPointer
	MAX-ACCESS	read-only
	STATUS		current
	DESCRIPTION	"OID for RTP"
	::= {saHpiHotSwapEntry 10}
	
--/*******************************************************************************
-- * ********************************************************************************
-- * ********** ********** ********** Resource Data Record ********** **********
-- * **********
-- * ********************************************************************************
-- * *******************************************************************************/

hpiResources	OBJECT IDENTIFIER ::= { hpi 3 }


saHpiRdrCount OBJECT-TYPE
	SYNTAX		Counter32
	MAX-ACCESS	read-only
	STATUS		current
	DESCRIPTION	"Number of resource data records in this system."
	::= {hpiResources 1}

saHpiRdrTable OBJECT-TYPE
        SYNTAX          SEQUENCE OF SaHpiRdrEntry
        MAX-ACCESS      not-accessible
        STATUS          current
        DESCRIPTION     "A table definining RDR records."
        ::= {hpiResources 2}

saHpiRdrEntry OBJECT-TYPE
        SYNTAX          SaHpiRdrEntry
        MAX-ACCESS      not-accessible
        STATUS          current
        DESCRIPTION 	" The following describes the different types of records that exist within a
         RDR repository and the RDR super-structure to all of the specific RDR types
         (sensor, inventory data, watchdog, etc.)."
        INDEX   { saHpiDomainID, saHpiResourceID, saHpiRdrRecordId, saHpiRdrType }

        ::= {saHpiRdrTable 1} 
                                                 
SaHpiRdrEntry ::= SEQUENCE {
	saHpiRdrRecordId	Unsigned32,
	saHpiRdrType		INTEGER,
	saHpiRdrEntityPath	OCTET STRING,
	saHpiRdr		RowPointer,
	saHpiRdrId		Counter32,
	saHpiRdrRTP		RowPointer
	}

saHpiRdrRecordId OBJECT-TYPE
        SYNTAX          Unsigned32
        MAX-ACCESS      read-only
        STATUS          current
        DESCRIPTION     "Record Id for the RDR entry."
        ::= {saHpiRdrEntry 1}

saHpiRdrType OBJECT-TYPE
        SYNTAX          INTEGER {
				undefined (0),
              			noRecord (1),
				ctrlRdr (2),
        			sensorRdr (3),
              			inventoryRdr (4),
        	      		watchdogRdr (5)
			}
        MAX-ACCESS      read-only
        STATUS          current
        DESCRIPTION     "Type of RDR entry."
        ::= {saHpiRdrEntry 2}

saHpiRdrEntityPath OBJECT-TYPE
        SYNTAX          OCTET STRING
        MAX-ACCESS      read-only
        STATUS          current
        DESCRIPTION     "
	If resource manages a FRU, entity path of the FRU.
        If resource manages a single entity, entity path of 
	that entity. 
	If resource manages multiple entities, the entity path 
	of the 'primary' entity managed by the resource.  
	
	Must be set to the same value in every domain which 
	contains this resource.

	This object converts HPI's saHpiEntityPathT structure 
	and an OpenHPI canonical string. The canonical string is 
	formed by removing the SAHPI_ENT_ prefix from the 
	HPI types, and creating tuples for the entity types. 
	
	Order of significance is inverted to make entity paths 
	look more like Unix directory structure. It is also assumed 
	that {ROOT,0} exists implicitly before all of these entries. 
	
	For example:
 	 {SYSTEM_CHASSIS,2}{PROCESSOR_BOARD,0} "
        ::= {saHpiRdrEntry 3}


saHpiRdr OBJECT-TYPE
	SYNTAX		RowPointer
	MAX-ACCESS	read-only
	STATUS		current
	DESCRIPTION	"Forward pointer to one of the four types of tables:

	     saHpiCtrlRec        
	     saHpiSensorRec
	     saHpiInventoryRec
	     saHpiWatchdogRec"
	::= {saHpiRdrEntry 4}

saHpiRdrId OBJECT-TYPE
        SYNTAX          Counter32
        MAX-ACCESS      read-only
        STATUS          current
        DESCRIPTION     "Id of the RDR entry. "
        ::= {saHpiRdrEntry 5}

saHpiRdrRTP OBJECT-TYPE
	SYNTAX          RowPointer
	MAX-ACCESS      read-only
	STATUS          current
	DESCRIPTION     "Forward pointer to the RTP entry. Another method to match 
	the RPT and RDR is to compare the EntityPath, but this is much easier. "
	::= {saHpiRdrEntry 6}

--/*******************************************************************************
-- * ********************************************************************************
-- * ********** ********** ********** Control Resource Data Records **********
-- * ********** **********
-- * ********************************************************************************
-- * *******************************************************************************/

saHpiCtrlCount OBJECT-TYPE
	SYNTAX		Counter32
	MAX-ACCESS	read-only
	STATUS		current
	DESCRIPTION	"The number of control resource data records in the system."
	::= {hpiResources 3}

saHpiCtrlTable OBJECT-TYPE
	SYNTAX		SEQUENCE OF SaHpiCtrlEntry
	MAX-ACCESS	not-accessible
	STATUS		current
	DESCRIPTION	"A table definining Control Resource Data Records."
	::= {hpiResources 4}
		

saHpiCtrlEntry OBJECT-TYPE
	SYNTAX		SaHpiCtrlEntry
	MAX-ACCESS	not-accessible
	STATUS		current
	DESCRIPTION
		"Definition of the control resource data record."
	INDEX	{ saHpiDomainID, saHpiResourceID, saHpiCtrlNum }
	::= {saHpiCtrlTable 1}


SaHpiCtrlEntry ::= SEQUENCE {
	saHpiCtrlNum		Unsigned32,
	saHpiCtrlOutputType	INTEGER,
	saHpiCtrlIgnore		TruthValue,
	saHpiCtrlType		INTEGER,
	saHpiCtrlState		OCTET STRING,
	saHpiCtrlAttributes	OCTET STRING,
	saHpiCtrlOem		Unsigned32, 
	saHpiCtrlTextType	INTEGER,
	saHpiCtrlTextLanguage	INTEGER,
	saHpiCtrlText		OCTET STRING,
	saHpiCtrlRDR		RowPointer
}


saHpiCtrlNum OBJECT-TYPE 
	SYNTAX		Unsigned32	
	MAX-ACCESS	read-only
	STATUS		current
	DESCRIPTION	"The control number "
	::= {saHpiCtrlEntry 1}



saHpiCtrlOutputType OBJECT-TYPE 
	SYNTAX		INTEGER {
				undefined (0),
				generic (1), 
				led (2), 
				fanSpeed (3), 
				dryContactClosure (4),
				powerSupplyInhibit (5),
				audible (6), 
				frontPanelLockout (7),
				powerInterlock (8), 
				powerState (9),
				lcdDisplay (10), 
				oem (11)
			}
	MAX-ACCESS	read-only
	STATUS		current
	DESCRIPTION	"
	This enumeration defines the what the control's output will be.  "
	::= {saHpiCtrlEntry 2}

saHpiCtrlIgnore OBJECT-TYPE 
	SYNTAX		TruthValue
	MAX-ACCESS	read-only
	STATUS		current
	DESCRIPTION	"Ignore control completly (entity not present, disabled, etc) "
	::= {saHpiCtrlEntry 3}

saHpiCtrlType OBJECT-TYPE 
	SYNTAX		INTEGER {
				undefined (0),
           			digital(1),
            			discrete(2),
            			analog(3),
            			stream(4),
            			text(5),
            			oem(193)
			}
	MAX-ACCESS	read-only
	STATUS		current
	DESCRIPTION	"This enumerated type defines the different types of
	generic controls. "
	::= {saHpiCtrlEntry 4}


saHpiCtrlState OBJECT-TYPE
	SYNTAX		OCTET STRING (SIZE(1|4|9))
	MAX-ACCESS	read-write
	STATUS		current
	DESCRIPTION	"
  	This attribute represents the current setting of the control.  It must
         be interpreted in the context of saHpiCtrlType.
	if you wish to change the values of the data, this is the object
	to use.

        digital  - Unsigned 32bit integer (4 octets) defined as:
                     off(1)
                     on(2),
                     pulseOff(3),
                     pulseOn(4),
                     auto(256)
        discrete - Unsigned 32bit integer  (4 octets)

        analog   - octets 1-4 represent the value specified in
		   network byte order.

        stream   - A stream control is represented as follows:
                     octet 1    - repeat flag
                     octets 2-5 - count of octets of data stored in the stream specified 
                                  in network byte order.
                     octets 6-9 - contain the stream data.

        text     - Text control attributes are represented as follows:
                     octet 1    - Line number (255 indicates all lines).
				When reading:
				Note that depending on the data type and 
				language, the text may be encoded in 2-byte 
				Unicode, which requires two bytes of data per
				character.

				When writting:
				If less than a full line of data is written, 
				the control will clear all spaces beyond 
				those written on the line. Thus writing a
				zero-length string will clear the addressed line. 
				It is also possible to include more characters 
				in the text passed in the CtrlState structure 
				than will fit on one line; in this case, 
				the control will 'wrap' to the next line 
				(still clearing the trailing characters on the
				last line written).

		The data will be in saHpiCtrlTextType, 
		saHpiCtrlTextLanguage, and saHpiCtrlText.


        oem      - An oem control is represented as follows:
                     octets 1-4   - manufacturer ID in network byte order

		The oem text data is located in saHpiCtrlText.
		The saHpiCtrlTextType and saHpiCtrlTextLanguage are both
		set to undefined (0).
	"
    REFERENCE 
        "Derived from typedef described in the SAI-HPI-A.01.01 pages 93, 94."
	 
	::= {saHpiCtrlEntry 5}

saHpiCtrlAttributes	OBJECT-TYPE
	SYNTAX		OCTET STRING(SIZE(4|9|12|262|270))
	MAX-ACCESS	read-only
	STATUS		current
	DESCRIPTION	"

	This object represents certain attributes of the control.
	It must be interpreted in the context of saHpiCtrlType.
	This object augments the data in saHpiCtrlState.

	analog	- Analog information is represented as follows:

		     octet 1-4 - Min value in network byte order
		     octet 5-8 - Max value in network byte order.
		     octet 9-12 - Default value in network byte order.

	digital  - 4 octet value in network byte order
	discrete - 4 octet value in network byte order
	stream   - 9 octet values in network byte order represented as:
                     octet 1    - repeat flag
                     octets 2-5 - count of octets of data stored in the stream 
				  specified in network byte order.
                     octets 6-9 - contain the stream data.

	text	- Text control attributes are represented as follows:
		  octet 1	- max characters	
		  octet 2	- max lines.
		  octet 3	- Language.  The possible values are from
				  1 to 137. Each values stands for a different
				  language. The enumerations are:
				  undef(1), afar(2), abkhazian(3),afrikaans(4),
				  amharic(5),arabic(6), etc ...

				  Look in saHpiCtrlTextLanguage object for
				  all possible language enumerations.

		  octet 4 	- encoding.  The possible values are:
				binary(1):
				  String of bytes, any values legal

				bcdplus(2)
				  String of 0-9, space, dash, period ONLY

				ascii6(3)
				  Reduced ASCII character set: 0x20-0x5F ONLY

				language(4)
				  ASCII or UNICODE depending on language 

		  octet 5	- line number.
		  octet 6	- length of data.
		  octet 7-n	- data to display (where max(n) is 262).

	oem	- An oem control is represented as follows:
		 octet 1-4	- manufacturer ID in network byte order.
		 octets 5-14	- configuration data.
		 octet 15	- body length.
		 octets 14-n	- default state (where max(n) is 270).
	" 
    REFERENCE 
        "Derived from typedef described in the SAI-HPI-A.01.01 pages 92, 93, 94."
	::= {saHpiCtrlEntry 6}

saHpiCtrlOem OBJECT-TYPE
	SYNTAX		Unsigned32
        MAX-ACCESS      read-only
	STATUS          current
	DESCRIPTION     "Reserved for OEM use"
	::= {saHpiCtrlEntry 7}

saHpiCtrlTextType OBJECT-TYPE 
	SYNTAX		INTEGER {
				undefined(0),
				binary(1), 
				bcdplus(2), 
				ascii6(3),
				language(4)
			}
	MAX-ACCESS	read-write
	STATUS		current
	DESCRIPTION	"
	Defines the type of data the saHpiCtrlText is
	encoded as:
	 binary(1):
		  String of bytes, any values legal

         bcdplus(2)
		String of 0-9, space, dash, period ONLY

         ascii6(3)
		Reduced ASCII character set: 0x20-0x5F ONLY

         language(4)
		ASCII or UNICODE depending on language
	"
	::= {saHpiCtrlEntry 8}

saHpiCtrlTextLanguage OBJECT-TYPE
	SYNTAX		INTEGER {
				undefined (0),
				unknown (1),
				afar (2),
				abkhazian (3),
				afrikaans (4),
				amharic (5),
				arabic (6),
				assamese (7),
				aymara (8),
				azerbaijani (9),
				bashkir (10),
				byelorussian (11),
				bulgarian (12),
				bihari (13),
				bislama (14),
				bengali (15),
				tibetan (16),
				breton (17),
				catalan (18),
				corsican (19),
				czech (20),
				welsh (21),
				danish (22),
				german (23),
				bhutani (24),
				greek (25),
				english (26),
				esperanto (27),
				spanish (28),
				estonian (29),
				basque (30),
				persian (31),
				finnish (32),
				fiji (33),
				faeroese (34),
				french (35),
				frisian (36),
				irish (37),
				scotsgaelic (38),
				galician (39),
				guarani (40),
				gujarati (41),
				hausa (42),
				hindi (43),
				croatian (44),
				hungarian (45),
				armenian (46),
				interlingua (47),
				interlingue (48),
				inupiak (49),
				indonesian (50),
				icelandic (51),
				italian (52),
				hebrew (53),
				japanese (54),
				yiddish (55),
				javanese (56),
				georgian (57),
				kazakh (58),
				greenlandic (59),
				cambodian (60),
				kannada (61),
				korean (62),
				kashmiri (63),
				kurdish (64),
				kirghiz (65),
				latin (66),
				lingala (67),
				laothian (68),
				lithuanian (69),
				latvianlettish (70),
				malagasy (71),
				maori (72),
				macedonian (73),
				malayalam (74),
				mongolian (75),
				moldavian (76),
				marathi (77),
				malay (78),
				maltese (79),
				burmese (80),
				nauru (81),
				nepali (82),
				dutch (83),
				norwegian (84),
				occitan (85),
				afanoromo (86),
				oriya (87),
				punjabi (88),
				polish (89),
				pashtopushto (90),
				portuguese (91),
				quechua (92),
				rhaetoromance (93),
				kirundi (94),
				romanian (95),
				russian (96),
				kinyarwanda (97),
				sanskrit (98),
				sindhi (99),
				sangro (100),
				serbocroatian (101),
				singhalese (102),
				slovak (103),
				slovenian (104),
				samoan (105),
				shona (106),
				somali (107),
				albanian (108),
				serbian (109),
				siswati (110),
				sesotho (111),
				sudanese (112),
				swedish (113),
				swahili (114),
				tamil (115),
				telugu (116),
				tajik (117),
				thai (118),
				tigrinya (119),
				turkmen (120),
				tagalog (121),
				setswana (122),
				tonga (123),
				turkish (124),
				tsonga (125),
				tatar (126),
				twi (127),
				ukrainian (128),
				urdu (129),
				uzbek (130),
				vietnamese (131),
				volapuk (132),
				wolof (133),
				xhosa (134),
				yoruba (135),
				chinese (136),
				zulu (137)
			}
        MAX-ACCESS      read-write
	STATUS          current
	DESCRIPTION     "
	This enumeration lists all of the languages that can be 
	associated with text.  Undef (0) indicates that 
	the language is unspecified or unknown.  "
	::= {saHpiCtrlEntry 9}

saHpiCtrlText OBJECT-TYPE
        SYNTAX          OCTET STRING(SIZE(0..255))
        MAX-ACCESS      read-write
        STATUS          current
        DESCRIPTION     
	"This value is only filled if the saHpiCtrlType
	is set to text(5) or oem(193). 

	if saHpiCtrlType == text(5),
		
The value will contain the line of text (the line
number is determined by saHpiCtrlState)  or if the line number
passed is 255,  this object will have the entire text of the control, 
or as much of it as will fit in this object.

This value will consist of the text of all the lines concatenated, 
using the maximum number of characters for each line 
(no trimming of trailing blanks).

Note that depending on the data type and language, the text may be
encoded in 2-byte Unicode, which requires two bytes of data per
character. 
Note that the number of lines and columns in a text control
can be obtained from the saHpiCtrlAttributes.

When writing, if less than a full line of data is written, 
the control will clear all spaces beyond those written on the line. 
Thus writing a zero-length string will clear the addressed line. 
It is also possible to include more characters in the text passed 
in than will fit on one line; in this case, the control will
'wrap' to the next line (still clearing the trailing characters 
on the last line written).	

	if saHpiCtrlType == oem(193),

	Contains the OEM specific data. Max length is 255 bytes.
	"
	REFERENCE
	"Derieved from typedef and function calls described in
	SAI-HPI-A.01.01 pages 93,94."
	::= {saHpiCtrlEntry 10}

saHpiCtrlRDR OBJECT-TYPE
	SYNTAX          RowPointer
	MAX-ACCESS      read-only
	STATUS          current
	DESCRIPTION     "Pointer to RDR for this Control Resource Data Record."
	::= {saHpiCtrlEntry 11}


--/*******************************************************************************
-- * ********************************************************************************
-- * ********** ********** ********** Sensor Resource Data Records **********
-- * ********** **********
-- * ********************************************************************************
-- * *******************************************************************************/


saHpiSensorCount OBJECT-TYPE
	SYNTAX		Counter32
	MAX-ACCESS	read-only
	STATUS		current
	DESCRIPTION	"The number of sensor resource data records in the system."
	::= {hpiResources 5}

saHpiSensorTable OBJECT-TYPE
        SYNTAX          SEQUENCE OF SaHpiSensorEntry
        MAX-ACCESS      not-accessible
        STATUS          current
        DESCRIPTION     "A table definining Sensors records."
        ::= {hpiResources 6}

saHpiSensorEntry OBJECT-TYPE
	SYNTAX		SaHpiSensorEntry
        MAX-ACCESS      not-accessible
        STATUS          current
        DESCRIPTION
        " This is the sensor resource data record which
	describes all of the static  data associated with a sensor."
        INDEX   { saHpiDomainID, saHpiResourceID, saHpiSensorIndex }
        ::= {saHpiSensorTable 1}

SaHpiSensorEntry ::= SEQUENCE {
	saHpiSensorIndex			Unsigned32,
	saHpiSensorType			INTEGER,
	saHpiSensorCategory			INTEGER,
	saHpiSensorEventsCategoryControl	INTEGER,
	saHpiSensorEventsSupported		OCTET STRING,
	saHpiSensorStatus			INTEGER,
	saHpiSensorAssertEvents			OCTET STRING,
	saHpiSensorDeassertEvents		OCTET STRING,
	saHpiSensorIgnore			TruthValue,
	saHpiSensorReadingFormats		Unsigned32,
	saHpiSensorIsNumeric                   TruthValue,
	saHpiSensorSignFormat                  INTEGER,
	saHpiSensorBaseUnits                   INTEGER,
	saHpiSensorModifierUnits               INTEGER,
	saHpiSensorModifierUse                 INTEGER,

	saHpiSensorFactorsStatic		TruthValue,
	saHpiSensorFactors			OCTET STRING,
	saHpiSensorFactorsLinearization	INTEGER,
	saHpiSensorPercentage 			TruthValue,

	saHpiSensorRangeFlags			OCTET STRING,
	saHpiSensorHasThresholds		TruthValue,
	saHpiSensorThresholdCapabilities	INTEGER,
	saHpiSensorOEM				Unsigned32,
	saHpiSensorRDR				RowPointer
	}


saHpiSensorIndex OBJECT-TYPE
        SYNTAX          Unsigned32
        MAX-ACCESS      read-only
        STATUS          current
        DESCRIPTION     "The sensor number. "
        ::= {saHpiSensorEntry 1}


saHpiSensorType OBJECT-TYPE
        SYNTAX          INTEGER {
				undefined (0),
				temperature (2),
				voltage (3),
				current (4),
				fan (5),
				physicalSecurity (6),
				platformViolation (7),
				processor (8),
				powerSupply (9),
				powerUnit (10),
				coolingDevice (11),
				otherUnitsBasedSensor (12),
				memory (13),
				driveSlot (14),
				postMemoryResize (15),
				systemFwProgress (16),
				eventLoggingDisabled (17),
				reserved1 (18),
				systemEvent (19),
				criticalInterrupt (20),
				button (21),
				moduleBoard (22),
				microcontrollerCoProcessor (23),
				addinCard (24),
				chassis (25),
				chipSet (26),
				otherFru (27),
				cableInterconnect (28),
				terminator (29),
				systemBootInitiated (30),
				bootError (31),
				osBoot (32),
				osCriticalStop (33),
				slotConnector (34),
				systemACPIPowerState (35),
				reserved2 (36),
				platformAlert (37),
				entityPresence (38),
				monitorAsicIC (39),
				lan (40),
				managementSubsystemHealth (41),
				battery (42),
				operational (162),
				oemSensor (194)
			}
        MAX-ACCESS      read-only
        STATUS          current
        DESCRIPTION     "General sensor type. "
        ::= {saHpiSensorEntry 2}

saHpiSensorCategory OBJECT-TYPE
        SYNTAX          INTEGER {
				undefined (0),
				unspecified (1),
				threshold (2),
				usage (3),
				state (4),
				predFail (5),
				limit (6),
				performance (7),
				severity (8),
				presence (9),
				enable (10),
				availability (11),
				redundancy (12),
				user (127),
				generic (128)
			}
        MAX-ACCESS      read-only
        STATUS          current
        DESCRIPTION     "Sensors category.
			
	 Sensor events contain an event category and event state. 
	Depending on the event category, the event states take on 
	different meanings for events generated by specific sensors.
			
	The generic(128) category can be used for discrete sensors which 
	have state meanings other than those identified with other event 
	categories.
	"		
        ::= {saHpiSensorEntry 3}

saHpiSensorEventsCategoryControl OBJECT-TYPE
        SYNTAX          INTEGER {
				undefined (0),
				perEvent(1),
				entireSensor(2),
				globalDisable(3),
				noEvents(4)
			}
        MAX-ACCESS      read-only
        STATUS          current
        DESCRIPTION     "Event Control
			
			 This type defines how sensor event messages can be controlled (can be turned 
			 off and on for each type of event, etc.).
			
			    perEvent(1) ,      Event message control per event 
			    entireSensor(2),   Control for entire sensor only 
			    globalDisable(3),  Global disable of events only 
			    noEvents(4)        Events not supported 
			"
        ::= {saHpiSensorEntry 4}

saHpiSensorEventsSupported OBJECT-TYPE
        SYNTAX          OCTET STRING 
        MAX-ACCESS      read-only
        STATUS          current
        DESCRIPTION     "Bit mask of event states supported.
	The following event states are specified relative to the 
	categories listed in saHpiSensorCategory. The event types 
	are only valid for their given category. Each set of 
	events is labeled as to which category it belongs to.
	Each event will have only one event state associated with it. 
	When retrieving the event status or event enabled status a 
	bit mask of all applicable event states is used. 

	Similarly, when setting the event enabled status a bit mask 
	of all applicable event states is used.  

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorEntry 5}

saHpiSensorStatus OBJECT-TYPE
	SYNTAX		INTEGER {
				undefined (0),
				eventsEnabled(129),
				scanEnabled(65),				
				busy(33),
				eventsEnabledandscanEndabled(193),
				eventsEnabledandbusy(161),
				scanEnabledandBusy(97),
				eventsEnabledandscanEnabledandBusy(225)	
			} 
	MAX-ACCESS	read-write
	STATUS		current
	DESCRIPTION	
	"The sensor status structure is used to determine if sensor 	
	scanning is enabled and if events are enabled. If events are 
	enabled, the structure will have valid data for the outstanding 
	sensor event states.    "
	::= {saHpiSensorEntry 6}
	

saHpiSensorAssertEvents OBJECT-TYPE
	SYNTAX		OCTET STRING
	MAX-ACCESS	read-write
	STATUS		current
	DESCRIPTION	
	"This object provides the ability to get the disable or enable event 
message generation status for individual sensor events. The sensor
event states are relative to the event category specified by the
sensor. See the saHpiEventCategory object for more information.

A event state in this object indicates that an event
will be generated when the corresponding event state 
changes from de-asserted to asserted on that sensor. "
	::= {saHpiSensorEntry 7}


saHpiSensorDeassertEvents OBJECT-TYPE
	SYNTAX		OCTET STRING	
	MAX-ACCESS	read-write
	STATUS		current
	DESCRIPTION	
	"This object provides the ability to get the disable or enable event 
message generation status for individual sensor events. The sensor
event states are relative to the event category specified by the
sensor. See the saHpiEventCategory object for more information.

A event state  in this object indicates that an event
will be generated when the corresponding event state 
changes from asserted to de-asserted on that sensor. "
	::= {saHpiSensorEntry 8}


saHpiSensorIgnore OBJECT-TYPE
        SYNTAX          TruthValue
        MAX-ACCESS      read-only
        STATUS          current
        DESCRIPTION     "Ignore sensor (entity not present, disabled, etc.)

	IBM-KR: If this is 'false' then this sensor wouldn't show up at all, would it?"
        ::= {saHpiSensorEntry 9}

saHpiSensorReadingFormats OBJECT-TYPE
        SYNTAX          Unsigned32 (1..7)
        MAX-ACCESS      read-only
        STATUS          current
        DESCRIPTION     "
	Indicates if sensor supports readings in raw, interpreted,
	and/or event status formats
	 
	SAHPI_SRF_RAW         0x01
 	SAHPI_SRF_INTERPRETED 0x02
 	SAHPI_SRF_EVENT_STATE 0x04

	"
        ::= {saHpiSensorEntry 10}

saHpiSensorIsNumeric OBJECT-TYPE
        SYNTAX          TruthValue
        MAX-ACCESS      read-only
        STATUS          current
        DESCRIPTION     "If FALSE, rest of this structure is not meaningful."
        ::= {saHpiSensorEntry 11}

saHpiSensorSignFormat OBJECT-TYPE
        SYNTAX          INTEGER {
				undefined (0),
				unsigned(1),
				sdf1SComplement(2),
				sdf2SComplement(3)
			}
        MAX-ACCESS      read-only
        STATUS          current
        DESCRIPTION     "Sign Format
			 
	This type defines what the sign format of the sensor's raw value is 
	(1's complement, unsigned, etc.).  "
        ::= {saHpiSensorEntry 12}

saHpiSensorBaseUnits OBJECT-TYPE
        SYNTAX          INTEGER {
				undefined (0),
				unspecified (1),
				degreesC (2),
				degreesF (3),
				degreesK (4),
				volts (5),
				amps (6),
				watts (7),
				joules (8),
				coulombs (9),
				va (10),
				nits (11),
				lumen (12),
				lux (13),
				candela (14),
				kpa (15),
				psi (16),
				newton (17),
				cfm (18),
				rpm (19),
				hz (20),
				microsecond (21),
				millisecond (22),
				second (23),
				minute (24),
				hour (25),
				day (26),
				week (27),
				mil (28),
				inches (29),
				feet (30),
				cuIn (31),
				cuFeet (32),
				mm (33),
				cm (34),
				m (35),
				cuCm (36),
				cuM (37),
				liters (38),
				fluidOunce (39),
				radians (40),
				steradians (41),
				revolutions (42),
				cycles (43),
				gravities (44),
				ounce (45),
				pound (46),
				ftLb (47),
				ozIn (48),
				gauss (49),
				gilberts (50),
				henry (51),
				millihenry (52),
				farad (53),
				microfarad (54),
				ohms (55),
				siemens (56),
				mole (57),
				becquerel (58),
				ppm (59),
				reserved (60),
				decibels (61),
				dba (62),
				dbc (63),
				gray (64),
				sievert (65),
				colorTempDegK (66),
				bit (67),
				kilobit (68),
				megabit (69),
				gigabit (70),
				byte (71),
				kilobyte (72),
				megabyte (73),
				gigabyte (74),
				word (75),
				dword (76),
				qword (77),
				line (78),
				hit (79),
				miss (80),
				retry (81),
				reset (82),
				overrun (83),
				underrun (84),
				collision (85),
				packets (86),
				messages (87),
				characters (88),
				errors (89),
				correctableErrors (90),
				uncorrectableErrors (91)
			}
        MAX-ACCESS      read-only
        STATUS          current
        DESCRIPTION     "Base units (meters, etc.). 
	This is a list of all the sensor units supported by HPI."
        ::= {saHpiSensorEntry 13}

saHpiSensorModifierUnits OBJECT-TYPE
        SYNTAX          INTEGER {
				undefined (0),
				unspecified (1),
				degreesC (2),
				degreesF (3),
				degreesK (4),
				volts (5),
				amps (6),
				watts (7),
				joules (8),
				coulombs (9),
				va (10),
				nits (11),
				lumen (12),
				lux (13),
				candela (14),
				kpa (15),
				psi (16),
				newton (17),
				cfm (18),
				rpm (19),
				hz (20),
				microsecond (21),
				millisecond (22),
				second (23),
				minute (24),
				hour (25),
				day (26),
				week (27),
				mil (28),
				inches (29),
				feet (30),
				cuIn (31),
				cuFeet (32),
				mm (33),
				cm (34),
				m (35),
				cuCm (36),
				cuM (37),
				liters (38),
				fluidOunce (39),
				radians (40),
				steradians (41),
				revolutions (42),
				cycles (43),
				gravities (44),
				ounce (45),
				pound (46),
				ftLb (47),
				ozIn (48),
				gauss (49),
				gilberts (50),
				henry (51),
				millihenry (52),
				farad (53),
				microfarad (54),
				ohms (55),
				siemens (56),
				mole (57),
				becquerel (58),
				ppm (59),
				reserved (60),
				decibels (61),
				dba (62),
				dbc (63),
				gray (64),
				sievert (65),
				colorTempDegK (66),
				bit (67),
				kilobit (68),
				megabit (69),
				gigabit (70),
				byte (71),
				kilobyte (72),
				megabyte (73),
				gigabyte (74),
				word (75),
				dword (76),
				qword (77),
				line (78),
				hit (79),
				miss (80),
				retry (81),
				reset (82),
				overrun (83),
				underrun (84),
				collision (85),
				packets (86),
				messages (87),
				characters (88),
				errors (89),
				correctableErrors (90),
				uncorrectableErrors (91)
			}
        MAX-ACCESS      read-only
        STATUS          current
        DESCRIPTION     "Modifier unit (second, etc.).  
	This is a list of all the sensor units supported by HPI"
        ::= {saHpiSensorEntry 14}

saHpiSensorModifierUse OBJECT-TYPE
        SYNTAX          INTEGER {
				undefined (0),
				none(1),
				basicOverModifier(2),
				basicTimesModifier(3)
			}
        MAX-ACCESS      read-only
        STATUS          current
        DESCRIPTION     "Modifier Unit Use (msec, etc.).
			 
	This type defines how the modifier unit is used. For example: 
	base unit == meter, modifier unit == seconds, and
	 modifier unit use == basicOverModifier(1). 
	The resulting unit would be meters per second."			
        ::= {saHpiSensorEntry 15}

saHpiSensorFactorsStatic OBJECT-TYPE
        SYNTAX          TruthValue
        MAX-ACCESS      read-only
        STATUS          current
        DESCRIPTION     " True if the sensor factors are static. If 
			factors vary over sensor range, and are not
                        accessible through HPI."
        ::= {saHpiSensorEntry 16}


saHpiSensorFactors OBJECT-TYPE
	SYNTAX		OCTET STRING(SIZE (1..10))
        MAX-ACCESS      read-only
        STATUS          current
        DESCRIPTION     "
	This object represents certain attributes of the factor table.
	It must be interpreted in the context saHpiSensorFactorsT 
	(from the HPI specification). The information in this object
	is determined based on saHpiSensorFactorsStatic.

	Octets  are as follow:
	1-2		M_Factor (16-bit signed integer)
	3-4		B_Factor (16-bit signed integer)
	5-6		Accuracy Factor (16-but unsigned integer)
	7		Tolerance Factor (8-bit unsigned integer)
	8		Accuracy Exponent (8-bit unsigned integer)
	9		Result Exponent	(8-bit signed integer)
	10		B Exponent	(8-bit signed integer) "	
        ::= {saHpiSensorEntry 17}

saHpiSensorFactorsLinearization OBJECT-TYPE
        SYNTAX          INTEGER {
				undefined (0),
				unspecified (1),
				linear (2),
				ln (3),
				log10 (4),
				log2 (5),
				e (6),
				exp10 (7),
				exp2 (8),
				oneoverx (9),
				sqrx (10),
				cubex (11),
				sqrtx (12),
				cubertx (13),
				nonlinear (114),
				oem (115)
			}
        MAX-ACCESS      read-only
        STATUS          current
        DESCRIPTION     "Linearization"
        ::= {saHpiSensorEntry 18}

saHpiSensorPercentage OBJECT-TYPE
        SYNTAX          TruthValue
        MAX-ACCESS      read-only
        STATUS          current
        DESCRIPTION     "Is the value a percentage."
        ::= {saHpiSensorEntry 19}

saHpiSensorRangeFlags OBJECT-TYPE
	SYNTAX		OCTET STRING
	MAX-ACCESS	read-only
	STATUS		current
	DESCRIPTION	
	"Defines which range flags the sensor supports. They
	can be MIN, MAX, NOMINAL, NORMAL_MAX, NORMAL_MIN, or
	nothing if the sensor does not support any ranges."
	::= {saHpiSensorEntry 20}

saHpiSensorHasThresholds OBJECT-TYPE
        SYNTAX          TruthValue
        MAX-ACCESS      read-only
        STATUS          current
        DESCRIPTION     " True if the sensor supports threshold values."
        ::= {saHpiSensorEntry 21}

saHpiSensorThresholdCapabilities OBJECT-TYPE
	SYNTAX		INTEGER {
				undefined(0),
				raw(2),
				interpreted(3),
				rawAndInterpreted(4)
			}
	MAX-ACCESS	read-only
	STATUS		current
	DESCRIPTION	"
	If set to raw(2) the raw value in the
	threshold tables is used for reading/writing. 
	If set to interpreted(3) the interpreted value in the
	threshold tables is used for reading/writing. 
	If set to rawAndInterpreted(4) both raw value and interpreted
	value can be used for reading/writing."
	::= {saHpiSensorEntry 22}
	
saHpiSensorOEM OBJECT-TYPE
        SYNTAX          Unsigned32 
        MAX-ACCESS      read-only
        STATUS          current
        DESCRIPTION     " Reserved for OEM use."
        ::= {saHpiSensorEntry 23}

saHpiSensorRDR OBJECT-TYPE
	SYNTAX		RowPointer
	MAX-ACCESS	read-only
	STATUS		current
	DESCRIPTION	"Forward pointer to the RDR OID."
	::= {saHpiSensorEntry 24}

--
-- /*******************************************************************************
-- ********************************************************************************
-- **********                                                            **********
-- **********                    Sensors - readings                   **********
-- **********                                                            **********
-- ********************************************************************************
-- *******************************************************************************/

hpiSensor	OBJECT IDENTIFIER ::= { hpiResources 7 }

saHpiSensorReadingCurrentTable OBJECT-TYPE
        SYNTAX          SEQUENCE OF SaHpiSensorReadingCurrentEntry
        MAX-ACCESS      not-accessible
        STATUS          current
        DESCRIPTION     "A table definining current sensor readings."
        ::= {hpiSensor 1}

saHpiSensorReadingCurrentEntry OBJECT-TYPE
	SYNTAX		SaHpiSensorReadingCurrentEntry
        MAX-ACCESS      not-accessible
        STATUS          current
        DESCRIPTION
        " This is the sensor resource data record which
	describes the dynamic data associated with sensors."
        INDEX   { saHpiDomainID, saHpiResourceID, saHpiSensorIndex }
        ::= {saHpiSensorReadingCurrentTable 1}

SaHpiSensorReadingCurrentEntry ::= SEQUENCE {
	saHpiSensorReadingCurrentValuesPresent	INTEGER,
	saHpiSensorReadingCurrentRaw		Unsigned32,
	saHpiSensorReadingCurrentInterpreted	OCTET STRING,
	saHpiSensorReadingCurrentStatus		INTEGER,
	saHpiSensorReadingCurrentEventStatus	OCTET STRING	
	}

saHpiSensorReadingCurrentValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingCurrentEntry 1}

saHpiSensorReadingCurrentRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingCurrentEntry 2}

saHpiSensorReadingCurrentInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingCurrentEntry 3}

saHpiSensorReadingCurrentStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingCurrentEntry 4}
	
saHpiSensorReadingCurrentEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingCurrentEntry 5}



saHpiSensorReadingMaxTable OBJECT-TYPE
        SYNTAX          SEQUENCE OF SaHpiSensorReadingMaxEntry
        MAX-ACCESS      not-accessible
        STATUS          current
        DESCRIPTION     "A table definining current sensor readings."
        ::= {hpiSensor 2}

saHpiSensorReadingMaxEntry OBJECT-TYPE
	SYNTAX		SaHpiSensorReadingMaxEntry
        MAX-ACCESS      not-accessible
        STATUS          current
        DESCRIPTION
        " This is the sensor resource data record which
	describes the dynamic data associated with sensors."
        INDEX   { saHpiDomainID, saHpiResourceID, saHpiSensorIndex }
        ::= {saHpiSensorReadingMaxTable 1}

SaHpiSensorReadingMaxEntry ::= SEQUENCE {
	saHpiSensorReadingMaxValuesPresent	INTEGER,
	saHpiSensorReadingMaxRaw		Unsigned32,
	saHpiSensorReadingMaxInterpreted	OCTET STRING,
	saHpiSensorReadingMaxStatus		INTEGER,
	saHpiSensorReadingMaxEventStatus	OCTET STRING	
	}

saHpiSensorReadingMaxValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingMaxEntry 1}

saHpiSensorReadingMaxRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingMaxEntry 2}

saHpiSensorReadingMaxInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingMaxEntry 3}

saHpiSensorReadingMaxStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingMaxEntry 4}
	
saHpiSensorReadingMaxEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingMaxEntry 5}


saHpiSensorReadingMinTable OBJECT-TYPE
        SYNTAX          SEQUENCE OF SaHpiSensorReadingMinEntry
        MAX-ACCESS      not-accessible
        STATUS          current
        DESCRIPTION     "A table definining current sensor readings."
        ::= {hpiSensor 3}

saHpiSensorReadingMinEntry OBJECT-TYPE
	SYNTAX		SaHpiSensorReadingMinEntry
        MAX-ACCESS      not-accessible
        STATUS          current
        DESCRIPTION
        " This is the sensor resource data record which
	describes the dynamic data associated with sensors."
        INDEX   { saHpiDomainID, saHpiResourceID, saHpiSensorIndex }
        ::= {saHpiSensorReadingMinTable 1}

SaHpiSensorReadingMinEntry ::= SEQUENCE {
	saHpiSensorReadingMinValuesPresent	INTEGER,
	saHpiSensorReadingMinRaw		Unsigned32,
	saHpiSensorReadingMinInterpreted	OCTET STRING,
	saHpiSensorReadingMinStatus		INTEGER,
	saHpiSensorReadingMinEventStatus	OCTET STRING
	}

saHpiSensorReadingMinValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingMinEntry 1}

saHpiSensorReadingMinRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingMinEntry 2}

saHpiSensorReadingMinInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingMinEntry 3}

saHpiSensorReadingMinStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)			       
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingMinEntry 4}
	
saHpiSensorReadingMinEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingMinEntry 5}



saHpiSensorReadingNominalTable OBJECT-TYPE
        SYNTAX          SEQUENCE OF SaHpiSensorReadingNominalEntry
        MAX-ACCESS      not-accessible
        STATUS          current
        DESCRIPTION     "A table definining current sensor readings."
        ::= {hpiSensor 4}

saHpiSensorReadingNominalEntry OBJECT-TYPE
	SYNTAX		SaHpiSensorReadingNominalEntry
        MAX-ACCESS      not-accessible
        STATUS          current
        DESCRIPTION
        " This is the sensor resource data record which
	describes the dynamic data associated with sensors."
        INDEX   { saHpiDomainID, saHpiResourceID, saHpiSensorIndex }
        ::= {saHpiSensorReadingNominalTable 1}

SaHpiSensorReadingNominalEntry ::= SEQUENCE {
	saHpiSensorReadingNominalValuesPresent	INTEGER,
	saHpiSensorReadingNominalRaw		Unsigned32,
	saHpiSensorReadingNominalInterpreted	OCTET STRING,
	saHpiSensorReadingNominalStatus		INTEGER,
	saHpiSensorReadingNominalEventStatus	OCTET STRING
	}

saHpiSensorReadingNominalValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingNominalEntry 1}

saHpiSensorReadingNominalRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingNominalEntry 2}

saHpiSensorReadingNominalInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingNominalEntry 3}

saHpiSensorReadingNominalStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)				
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingNominalEntry 4}
	
saHpiSensorReadingNominalEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingNominalEntry 5}



saHpiSensorReadingNormalMaxTable OBJECT-TYPE
        SYNTAX          SEQUENCE OF SaHpiSensorReadingNormalMaxEntry
        MAX-ACCESS      not-accessible
        STATUS          current
        DESCRIPTION     "A table definining current sensor readings."
        ::= {hpiSensor 5}

saHpiSensorReadingNormalMaxEntry OBJECT-TYPE
	SYNTAX		SaHpiSensorReadingNormalMaxEntry
        MAX-ACCESS      not-accessible
        STATUS          current
        DESCRIPTION
        " This is the sensor resource data record which
	describes the dynamic data associated with sensors."
        INDEX   { saHpiDomainID, saHpiResourceID, saHpiSensorIndex }
        ::= {saHpiSensorReadingNormalMaxTable 1}

SaHpiSensorReadingNormalMaxEntry ::= SEQUENCE {
	saHpiSensorReadingNormalMaxValuesPresent	INTEGER,
	saHpiSensorReadingNormalMaxRaw		Unsigned32,
	saHpiSensorReadingNormalMaxInterpreted	OCTET STRING,
	saHpiSensorReadingNormalMaxStatus	INTEGER,
	saHpiSensorReadingNormalMaxEventStatus	OCTET STRING
	}

saHpiSensorReadingNormalMaxValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingNormalMaxEntry 1}

saHpiSensorReadingNormalMaxRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingNormalMaxEntry 2}

saHpiSensorReadingNormalMaxInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingNormalMaxEntry 3}

saHpiSensorReadingNormalMaxStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingNormalMaxEntry 4}
	
saHpiSensorReadingNormalMaxEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingNormalMaxEntry 5}



saHpiSensorReadingNormalMinTable OBJECT-TYPE
        SYNTAX          SEQUENCE OF SaHpiSensorReadingNormalMinEntry
        MAX-ACCESS      not-accessible
        STATUS          current
        DESCRIPTION     "A table definining current sensor readings."
        ::= {hpiSensor 6}

saHpiSensorReadingNormalMinEntry OBJECT-TYPE
	SYNTAX		SaHpiSensorReadingNormalMinEntry
        MAX-ACCESS      not-accessible
        STATUS          current
        DESCRIPTION
        " This is the sensor resource data record which
	describes the dynamic data associated with sensors."
        INDEX   { saHpiDomainID, saHpiResourceID, saHpiSensorIndex }
        ::= {saHpiSensorReadingNormalMinTable 1}

SaHpiSensorReadingNormalMinEntry ::= SEQUENCE {
	saHpiSensorReadingNormalMinValuesPresent	INTEGER,
	saHpiSensorReadingNormalMinRaw		Unsigned32,
	saHpiSensorReadingNormalMinInterpreted	OCTET STRING,
	saHpiSensorReadingNormalMinStatus	INTEGER,
	saHpiSensorReadingNormalMinEventStatus	OCTET STRING
	}

saHpiSensorReadingNormalMinValuesPresent OBJECT-TYPE
	SYNTAX		INTEGER {
				undefined(0),

				raw(2),
				interpreted(3),
				eventState(5),

				rawAndInterpreted(4),
				rawAndEventState(6),
				rawAndInterpretedAndEventState(8),

				interpretedAndEventState(7)
			}
	MAX-ACCESS	read-only
	STATUS		current
	DESCRIPTION
	"Each sensor may support one or more of raw, 
	interpreted, or event status representations of the sensor data."
	REFERENCE
	"Type derieved from SAF SAI-HPI-A.01.01 spec page 87."
	::= {saHpiSensorReadingNormalMinEntry 1}

saHpiSensorReadingNormalMinRaw OBJECT-TYPE
        SYNTAX          Unsigned32
        MAX-ACCESS      read-only
        STATUS          current
        DESCRIPTION     
	"Raw sensor reading. For example, analog sensos  raw value is 
	the raw value from the sensor (such as ticks per fan blade).
	
	This value to be completly understood, has to be read in the 
	context of:
	
	 - saHpiSensorSignFormat (which defines the sign format of this 
		value - 1's complement, unsigned ,etc),
	 - saHpiSensorBaseUnits (which defines the base units - meters, etc),
	 - saHpiSensorModifierUnits (modified units - seconds, etc),
	 - saHpiSensorModifierUse (defines how modifier value is used),
	 - saHpiSensorFactors and,
	 - saHpiSensorFactorsLinearization.

	"
        ::= {saHpiSensorReadingNormalMinEntry 2}

saHpiSensorReadingNormalMinInterpreted OBJECT-TYPE
	SYNTAX		OCTET STRING(SIZE(0..255))
	MAX-ACCESS	read-only
	STATUS		current
	DESCRIPTION
	"Interpreted reading of the sensor value. For example
	this value can be:

		'32.6F'
		'1900.33 rpm'
		'39 newton over cuM'
		'23123198918392.239998 gram over cuCm'
	"
	REFERENCE
	"Object derieved from SAF SAI-HPI-A.01.01 spec page 87."
	::= {saHpiSensorReadingNormalMinEntry 3}

saHpiSensorReadingNormalMinStatus OBJECT-TYPE
        SYNTAX          INTEGER {
				undefined (0),
				eventsEnabled(129),
				scanEnabled(65),				
				busy(33),
				eventsEnabledandscanEndabled(193),
				eventsEnabledandbusy(161),
				scanEnabledandBusy(97),
				eventsEnabledandscanEnabledandBusy(225)	
			}
        MAX-ACCESS      read-only
        STATUS          current
        DESCRIPTION
	"
	The sensor status  is used to determine if sensor scanning is 
	enabled and if events are enabled. If events are enabled, the 
	objects will have valid data for the outstanding sensor event states.
	"
	REFERENCE
	"Object derieved from SAF SAI-HPI-A.01.01 spec page 87."
	::= {saHpiSensorReadingNormalMinEntry 4}
	
saHpiSensorReadingNormalMinEventStatus OBJECT-TYPE
	SYNTAX		OCTET STRING
        MAX-ACCESS      read-only
        STATUS          current
        DESCRIPTION     "
	Event states for the sensor.

	A NULL value indicates not set/used.

	The event status values are specified as a list of
	possible string enumerations. For example for a sensor
	that is category severity, this object might hold the values:
	SAHPI_ES_MINOR_FROM_MORE,SAHPI_ES_MINOR_FROM_MORE'

	Depending on the category of the sensor, the possible values
	of this object differ.

	For the category = unspecified, the value can be:
		'SAHPI_ES_UNSPECIFIED'

	For threshold category, all of the possible values are:
		'SAHPI_ES_LOWER_MINOR,SAHPI_ES_LOWER_MAJOR,
 		SAHPI_ES_LOWER_MAJOR,SAHPI_ES_UPPER_MINOR,
 		SAHPI_ES_UPPER_MINOR,SAHPI_ES_UPPER_MINOR'

	For a usage category, all off the possible values are:
		'SAHPI_ES_IDLE, SAHPI_ES_ACTIVE, SAHPI_ES_BUSY'

	For state category, all of the possible values are:
		'SAHPI_ES_STATE_DEASSERTED, SAHPI_ES_STATE_ASSERTED'

	For predictive failure category, all of the possible values are:
		'SAHPI_ES_PRED_FAILURE_DEASSERT,
		 SAHPI_ES_PRED_FAILURE_ASSERT'

	For limit category, the possible values are: 	
		'SAHPI_ES_LIMIT_NOT_EXCEEDED,
		 SAHPI_ES_LIMIT_EXCEEDED'

	For performance category, the possible values are:
		'SAHPI_ES_PERFORMANCE_MET, 
		SAHPI_ES_PERFORMANCE_LAGS'

	For severity category, the possible values are:
		'SAHPI_ES_OK, SAHPI_ES_MINOR_FROM_OK,
		SAHPI_ES_MAJOR_FROM_LESS, SAHPI_ES_CRITICAL_FROM_LESS,
		SAHPI_ES_MINOR_FROM_MORE, SAHPI_ES_MAJOR_FROM_CRITICAL,
		SAHPI_ES_CRITICAL, SAHPI_ES_MONITOR
		SAHPI_ES_INFORMATIONAL'

	For presence category, the possible values are:
		'SAHPI_ES_ABSENT, SAHPI_ES_PRESENT'

	For enable category, the possible values are:
		'SAHPI_ES_DISABLED, SAHPI_ES_ENABLED'
			
	For availability category, the possible values are: 
		'SAHPI_ES_RUNNING, SAHPI_ES_TEST, SAHPI_ES_POWER_OFF,
		SAHPI_ES_ON_LINE, SAHPI_ES_OFF_LINE,
		SAHPI_ES_OFF_DUTY, SAHPI_ES_DEGRADED,
		SAHPI_ES_POWER_SAVE, SAHPI_ES_INSTALL_ERROR'

	For redundancy category, the possible values are:
		'SAHPI_ES_FULLY_REDUNDANT, SAHPI_ES_REDUNDANCY_LOST,
		SAHPI_ES_REDUNDANCY_DEGRADED, 
		SAHPI_ES_REDUNDANCY_LOST_SUFFICIENT_RESOURCES,
		SAHPI_ES_NON_REDUNDANT_SUFFICIENT_RESOURCES,
		SAHPI_ES_NON_REDUNDANT_INSUFFICIENT_RESOURCES,
		SAHPI_ES_REDUNDANCY_DEGRADED_FROM_FULL,
		SAHPI_ES_REDUNDANCY_DEGRADED_FROM_NON'

	For generic category, the possible values are:
		'SAHPI_ES_STATE_00, SAHPI_ES_STATE_01,
		SAHPI_ES_STATE_02, SAHPI_ES_STATE_03,
		SAHPI_ES_STATE_04, SAHPI_ES_STATE_05,
		SAHPI_ES_STATE_06, SAHPI_ES_STATE_07,
		SAHPI_ES_STATE_08, SAHPI_ES_STATE_09,
		SAHPI_ES_STATE_10, SAHPI_ES_STATE_11,
		SAHPI_ES_STATE_12, SAHPI_ES_STATE_13,
		SAHPI_ES_STATE_14'"
        ::= {saHpiSensorReadingNormalMinEntry 5}


--
-- Threshold values
--


saHpiSensorThdLowCriticalTable OBJECT-TYPE
        SYNTAX          SEQUENCE OF SaHpiSensorThdLowCriticalEntry
        MAX-ACCESS      not-accessible
        STATUS          current
        DESCRIPTION     "A table definining lower critical threshold values for
	sensor that supports raw or interpreted values."
        ::= {hpiSensor 7}

saHpiSensorThdLowCriticalEntry OBJECT-TYPE
	SYNTAX		SaHpiSensorThdLowCriticalEntry
        MAX-ACCESS      not-accessible
        STATUS          current
        DESCRIPTION
	"This is the sensor threshold data which defines the catastrophic lower 
	end of the range that impacts the functional status of the sensor."

        INDEX   { saHpiDomainID, saHpiResourceID, saHpiSensorIndex }
        ::= {saHpiSensorThdLowCriticalTable 1}

SaHpiSensorThdLowCriticalEntry ::= SEQUENCE {
	saHpiSensorThdLowCriticalIsReadable		TruthValue,
	saHpiSensorThdLowCriticalIsWritable		TruthValue,
	saHpiSensorThdLowCriticalIsFixed		TruthValue,
	saHpiSensorThdLowCriticalValuesPresent		INTEGER,
	saHpiSensorThdLowCriticalRaw			Unsigned32,
	saHpiSensorThdLowCriticalInterpreted		OCTET STRING
	}

saHpiSensorThdLowCriticalIsReadable	OBJECT-TYPE
	SYNTAX		TruthValue
	MAX-ACCESS	read-only
	STATUS		current
	DESCRIPTION
	"Defines if sensor threshold information can be read. 
	If set to 'false(2)' the saHpiSensorThdLowCriticalRaw is set to
	'-1' and saHpiSensorThdLowCriticalInterpreted is set to zero-length
	string."
	REFERENCE
	"Object derieved from SAF SAI-HPI-A.01.01 spec page 90 and 91."
	::= {saHpiSensorThdLowCriticalEntry 1}

saHpiSensorThdLowCriticalIsWritable	OBJECT-TYPE
	SYNTAX		TruthValue
	MAX-ACCESS	read-only
	STATUS		current
	DESCRIPTION
	"Defines if sensor threshold information can be written to. 

	If set to 'false(2)' writting to saHpiSensorThdLowCriticalRaw 
	and saHpiSensorThdLowCriticalInterpreted will not change the
	threshold values."
	REFERENCE
	"Object derieved from SAF SAI-HPI-A.01.01 spec page 90 and 91."
	::= {saHpiSensorThdLowCriticalEntry 2}

saHpiSensorThdLowCriticalIsFixed	OBJECT-TYPE
	SYNTAX		TruthValue
	MAX-ACCESS	read-only
	STATUS		current
	DESCRIPTION
	"Defines if sensor threshold information is fixed - cannot be changed.

	If set to 'false(2)' writting to saHpiSensorThdLowCriticalRaw 
	and saHpiSensorThdLowCriticalInterpreted will not change the
	threshold values."
	REFERENCE
	"Object derieved from SAF SAI-HPI-A.01.01 spec page 90 and 91."
	::= {saHpiSensorThdLowCriticalEntry 3}

saHpiSensorThdLowCriticalValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdLowCriticalEntry 4}

saHpiSensorThdLowCriticalRaw OBJECT-TYPE
        SYNTAX          Unsigned32
        MAX-ACCESS      read-write
        STATUS          current
        DESCRIPTION     
	"The raw (as unsigned 32 bit value) value which defines the catastrophic lower 
	end of the range that impacts the functional status of the sensor.

	Note:
	If 'saHpiSensorThdLowCriticalIsReadable' is set to 'true(1)', this value
	can be read. Otherwise the value is set to '-1'.

	If 'saHpiSensorThdLowCriticalisWriteable' is set to 'true(1)', this value
	can be changed. Otherwise this value can not be modified.
	After the write operation the value of interpreted object will change
	accordingly.
	
	Finally, if 'saHpiSensorThdLowCriticalIsFixed' objects is set to 'true(1)',
	this value can not be changed.
	"
        ::= {saHpiSensorThdLowCriticalEntry 5}

saHpiSensorThdLowCriticalInterpreted OBJECT-TYPE
	SYNTAX		OCTET STRING(SIZE(0..255))
	MAX-ACCESS	read-write
	STATUS		current
	DESCRIPTION
	"Interpreted threshold value which defines the catastrophic lower
	end of the range that impacts the functional status of the sensor.

	Example of this is:

		'32.6F'
		'1900.33 rpm'
		'39 newton over cuM'
		'23123198918392.239998 gram over cuCm'
	"
	REFERENCE
	"Object derieved from SAF SAI-HPI-A.01.01 spec page 87."
	::= {saHpiSensorThdLowCriticalEntry 6}



saHpiSensorThdLowMajorTable OBJECT-TYPE
        SYNTAX          SEQUENCE OF SaHpiSensorThdLowMajorEntry
        MAX-ACCESS      not-accessible
        STATUS          current
        DESCRIPTION     "A table definining severely degraded status at the
	lower end of critical threshold values for sensor that supports raw or 
	interpreted values."
        ::= {hpiSensor 8}

saHpiSensorThdLowMajorEntry OBJECT-TYPE
	SYNTAX		SaHpiSensorThdLowMajorEntry
        MAX-ACCESS      not-accessible
        STATUS          current
        DESCRIPTION
	"This is the sensor threshold data which defines severely degraded status
	status at the lower end of the range that impacts the functional status 
	of the sensor."
        INDEX   { saHpiDomainID, saHpiResourceID, saHpiSensorIndex }
        ::= {saHpiSensorThdLowMajorTable 1}

SaHpiSensorThdLowMajorEntry ::= SEQUENCE {
	saHpiSensorThdLowMajorIsReadable		TruthValue,
	saHpiSensorThdLowMajorIsWritable		TruthValue,
	saHpiSensorThdLowMajorIsFixed			TruthValue,
	saHpiSensorThdLowMajorValuesPresent		INTEGER,
	saHpiSensorThdLowMajorRaw			Unsigned32,
	saHpiSensorThdLowMajorInterpreted		OCTET STRING
	}

saHpiSensorThdLowMajorIsReadable	OBJECT-TYPE
	SYNTAX		TruthValue
	MAX-ACCESS	read-only
	STATUS		current
	DESCRIPTION
	"Defines if sensor threshold information can be read. 
	If set to 'false(2)' the saHpiSensorThdLowMajorRaw is set to
	'-1' and saHpiSensorThdLowMajorInterpreted is set to zero-length
	string."
	REFERENCE
	"Object derieved from SAF SAI-HPI-A.01.01 spec page 90 and 91."
	::= {saHpiSensorThdLowMajorEntry 1}

saHpiSensorThdLowMajorIsWritable	OBJECT-TYPE
	SYNTAX		TruthValue
	MAX-ACCESS	read-only
	STATUS		current
	DESCRIPTION
	"Defines if sensor threshold information can be written to. 

	If set to 'false(2)' writting to saHpiSensorThdLowMajorRaw 
	and saHpiSensorThdLowMajorInterpreted will not change the
	threshold values."
	REFERENCE
	"Object derieved from SAF SAI-HPI-A.01.01 spec page 90 and 91."
	::= {saHpiSensorThdLowMajorEntry 2}

saHpiSensorThdLowMajorIsFixed	OBJECT-TYPE
	SYNTAX		TruthValue
	MAX-ACCESS	read-only
	STATUS		current
	DESCRIPTION
	"Defines if sensor threshold information is fixed - cannot be changed.

	If set to 'false(2)' writting to saHpiSensorThdLowMajorRaw 
	and saHpiSensorThdLowMajorInterpreted will not change the
	threshold values."
	REFERENCE
	"Object derieved from SAF SAI-HPI-A.01.01 spec page 90 and 91."
	::= {saHpiSensorThdLowMajorEntry 3}

saHpiSensorThdLowMajorValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdLowMajorEntry 4}

saHpiSensorThdLowMajorRaw OBJECT-TYPE
        SYNTAX          Unsigned32
        MAX-ACCESS      read-write
        STATUS          current
        DESCRIPTION     
	"The raw (as unsigned 32 bit value) value which defines the severely
	degraded status at lower end of the range that impacts the functional 
	status of the sensor.

	Note:
	If 'saHpiSensorThdLowMajorIsReadable' is set to 'true(1)', this value
	can be read. Otherwise the value is set to '-1'.

	If 'saHpiSensorThdLowMajorisWriteable' is set to 'true(1)', this value
	can be changed. Otherwise this value can not be modified.
	After the write operation the value of interpreted object will change
	accordingly.
	
	Finally, if 'saHpiSensorThdLowMajorIsFixed' objects is set to 'true(1)',
	this value can not be changed.
	"
        ::= {saHpiSensorThdLowMajorEntry 5}

saHpiSensorThdLowMajorInterpreted OBJECT-TYPE
	SYNTAX		OCTET STRING(SIZE(0..255))
	MAX-ACCESS	read-write
	STATUS		current
	DESCRIPTION
	"Interpreted threshold value which defines the severely degraded
	status at the end of the range that impacts the functional status 
	of the sensor.

	Example of this is:

		'32.6F'
		'1900.33 rpm'
		'39 newton over cuM'
		'23123198918392.239998 gram over cuCm'
	"
	REFERENCE
	"Object derieved from SAF SAI-HPI-A.01.01 spec page 87."
	::= {saHpiSensorThdLowMajorEntry 6}

saHpiSensorThdLowMinorTable OBJECT-TYPE
        SYNTAX          SEQUENCE OF SaHpiSensorThdLowMinorEntry
        MAX-ACCESS      not-accessible
        STATUS          current
        DESCRIPTION     "A table definining lower minor threshold values for a sensor 
	that supports raw or interpreted values."
        ::= {hpiSensor 9}

saHpiSensorThdLowMinorEntry OBJECT-TYPE
	SYNTAX		SaHpiSensorThdLowMinorEntry
        MAX-ACCESS      not-accessible
        STATUS          current
        DESCRIPTION
	"This is the sensor threshold data which defines the degraded status
	at the lower end of the range that impacts the functional status of the sensor."

        INDEX   { saHpiDomainID, saHpiResourceID, saHpiSensorIndex }
        ::= {saHpiSensorThdLowMinorTable 1}

SaHpiSensorThdLowMinorEntry ::= SEQUENCE {
	saHpiSensorThdLowMinorIsReadable	TruthValue,
	saHpiSensorThdLowMinorIsWritable	TruthValue,
	saHpiSensorThdLowMinorIsFixed		TruthValue,
	saHpiSensorThdLowMinorValuesPresent	INTEGER,
	saHpiSensorThdLowMinorRaw		Unsigned32,
	saHpiSensorThdLowMinorInterpreted	OCTET STRING
	}


saHpiSensorThdLowMinorIsReadable	OBJECT-TYPE
	SYNTAX		TruthValue
	MAX-ACCESS	read-only
	STATUS		current
	DESCRIPTION
	"Defines if sensor threshold information can be read. 
	If set to 'false(2)' the saHpiSensorThdLowMinorRaw is set to
	'-1' and saHpiSensorThdLowMinorInterpreted is set to zero-length
	string."
	REFERENCE
	"Object derieved from SAF SAI-HPI-A.01.01 spec page 90 and 91."
	::= {saHpiSensorThdLowMinorEntry 1}

saHpiSensorThdLowMinorIsWritable	OBJECT-TYPE
	SYNTAX		TruthValue
	MAX-ACCESS	read-only
	STATUS		current
	DESCRIPTION
	"Defines if sensor threshold information can be written to. 

	If set to 'false(2)' writting to saHpiSensorThdLowMinorRaw 
	and saHpiSensorThdLowMinorInterpreted will not change the
	threshold values."
	REFERENCE
	"Object derieved from SAF SAI-HPI-A.01.01 spec page 90 and 91."
	::= {saHpiSensorThdLowMinorEntry 2}

saHpiSensorThdLowMinorIsFixed	OBJECT-TYPE
	SYNTAX		TruthValue
	MAX-ACCESS	read-only
	STATUS		current
	DESCRIPTION
	"Defines if sensor threshold information is fixed - cannot be changed.

	If set to 'false(2)' writting to saHpiSensorThdLowMinorRaw 
	and saHpiSensorThdLowMinorInterpreted will not change the
	threshold values."
	REFERENCE
	"Object derieved from SAF SAI-HPI-A.01.01 spec page 90 and 91."
	::= {saHpiSensorThdLowMinorEntry 3}

saHpiSensorThdLowMinorValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdLowMinorEntry 4}

saHpiSensorThdLowMinorRaw OBJECT-TYPE
        SYNTAX          Unsigned32
        MAX-ACCESS      read-write
        STATUS          current
        DESCRIPTION     
	"The raw (as unsigned 32 bit value) value which is the degraded status
	at the lower end of range that does not impact the functional status 
	of the sensor.

	Note:
	If 'saHpiSensorThdLowMinorIsReadable' is set to 'true(1)', this value
	can be read. Otherwise the value is set to '-1'.

	If 'saHpiSensorThdLowMinorisWriteable' is set to 'true(1)', this value
	can be changed. Otherwise this value can not be modified.
	After the write operation the value of interpreted object will change
	accordingly.
	
	Finally, if 'saHpiSensorThdLowMinorIsFixed' objects is set to 'true(1)',
	this value can not be changed.
	"
        ::= {saHpiSensorThdLowMinorEntry 5}

saHpiSensorThdLowMinorInterpreted OBJECT-TYPE
	SYNTAX		OCTET STRING(SIZE(0..255))
	MAX-ACCESS	read-write
	STATUS		current
	DESCRIPTION
	"Interpreted threshold value which is the degraded status at the lower 
	end that does not impact the functional status of the sensor. 
	
	Example of this value:	

		'32.6F'
		'1900.33 rpm'
		'39 newton over cuM'
		'23123198918392.239998 gram over cuCm'
	"
	REFERENCE
	"Object derieved from SAF SAI-HPI-A.01.01 spec page 87."
	::= {saHpiSensorThdLowMinorEntry 6}




saHpiSensorThdUpCriticalTable OBJECT-TYPE
        SYNTAX          SEQUENCE OF SaHpiSensorThdUpCriticalEntry
        MAX-ACCESS      not-accessible
        STATUS          current
        DESCRIPTION     "A table definining  catastrophic status at the
	upper end of critical threshold values for sensor that supports raw or 
	interpreted values."
        ::= {hpiSensor 10}

saHpiSensorThdUpCriticalEntry OBJECT-TYPE
	SYNTAX		SaHpiSensorThdUpCriticalEntry
        MAX-ACCESS      not-accessible
        STATUS          current
        DESCRIPTION
	"This is the sensor threshold data which defines  catastrophic status
	status at the upper end of the range that impacts the functional status 
	of the sensor."
        INDEX   { saHpiDomainID, saHpiResourceID, saHpiSensorIndex }
        ::= {saHpiSensorThdUpCriticalTable 1}

SaHpiSensorThdUpCriticalEntry ::= SEQUENCE {
	saHpiSensorThdUpCriticalIsReadable		TruthValue,
	saHpiSensorThdUpCriticalIsWritable		TruthValue,
	saHpiSensorThdUpCriticalIsFixed			TruthValue,
	saHpiSensorThdUpCriticalValuesPresent		INTEGER,
	saHpiSensorThdUpCriticalRaw			Unsigned32,
	saHpiSensorThdUpCriticalInterpreted		OCTET STRING
	}


saHpiSensorThdUpCriticalIsReadable	OBJECT-TYPE
	SYNTAX		TruthValue
	MAX-ACCESS	read-only
	STATUS		current
	DESCRIPTION
	"Defines if sensor threshold information can be read. 
	If set to 'false(2)' the saHpiSensorThdUpCriticalRaw is set to
	'-1' and saHpiSensorThdUpCriticalInterpreted is set to zero-length
	string."
	REFERENCE
	"Object derieved from SAF SAI-HPI-A.01.01 spec page 90 and 91."
	::= {saHpiSensorThdUpCriticalEntry 1}

saHpiSensorThdUpCriticalIsWritable	OBJECT-TYPE
	SYNTAX		TruthValue
	MAX-ACCESS	read-only
	STATUS		current
	DESCRIPTION
	"Defines if sensor threshold information can be written to. 

	If set to 'false(2)' writting to saHpiSensorThdUpCriticalRaw 
	and saHpiSensorThdUpCriticalInterpreted will not change the
	threshold values."
	REFERENCE
	"Object derieved from SAF SAI-HPI-A.01.01 spec page 90 and 91."
	::= {saHpiSensorThdUpCriticalEntry 2}

saHpiSensorThdUpCriticalIsFixed	OBJECT-TYPE
	SYNTAX		TruthValue
	MAX-ACCESS	read-only
	STATUS		current
	DESCRIPTION
	"Defines if sensor threshold information is fixed - cannot be changed.

	If set to 'false(2)' writting to saHpiSensorThdUpCriticalRaw 
	and saHpiSensorThdUpCriticalInterpreted will not change the
	threshold values."
	REFERENCE
	"Object derieved from SAF SAI-HPI-A.01.01 spec page 90 and 91."
	::= {saHpiSensorThdUpCriticalEntry 3}

saHpiSensorThdUpCriticalValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdUpCriticalEntry 4}

saHpiSensorThdUpCriticalRaw OBJECT-TYPE
        SYNTAX          Unsigned32
        MAX-ACCESS      read-write
        STATUS          current
        DESCRIPTION     
	"The raw (as unsigned 32 bit value) value which defines the 
	catastrophic status at upper end of the range that impacts the functional 
	status of the sensor.

	Note:
	If 'saHpiSensorThdUpCriticalIsReadable' is set to 'true(1)', this value
	can be read. Otherwise the value is set to '-1'.

	If 'saHpiSensorThdUpCriticalisWriteable' is set to 'true(1)', this value
	can be changed. Otherwise this value can not be modified.
	After the write operation the value of interpreted object will change
	accordingly.
	
	Finally, if 'saHpiSensorThdUpCriticalIsFixed' objects is set to 'true(1)',
	this value can not be changed.
	"
        ::= {saHpiSensorThdUpCriticalEntry 5}

saHpiSensorThdUpCriticalInterpreted OBJECT-TYPE
	SYNTAX		OCTET STRING(SIZE(0..255))
	MAX-ACCESS	read-write
	STATUS		current
	DESCRIPTION
	"Interpreted threshold value which defines the  catastrophic
	status at the upper end of the range that impacts the functional status 
	of the sensor.

	Example of this is:

		'32.6F'
		'1900.33 rpm'
		'39 newton over cuM'
		'23123198918392.239998 gram over cuCm'
	"
	REFERENCE
	"Object derieved from SAF SAI-HPI-A.01.01 spec page 87."
	::= {saHpiSensorThdUpCriticalEntry 6}


saHpiSensorThdUpMajorTable OBJECT-TYPE
        SYNTAX          SEQUENCE OF SaHpiSensorThdUpMajorEntry
        MAX-ACCESS      not-accessible
        STATUS          current
        DESCRIPTION     "A table definining severely degraded status at the
	upper end of critical threshold values for sensor that supports raw or 
	interpreted values."
        ::= {hpiSensor 11}

saHpiSensorThdUpMajorEntry OBJECT-TYPE
	SYNTAX		SaHpiSensorThdUpMajorEntry
        MAX-ACCESS      not-accessible
        STATUS          current
        DESCRIPTION
	"This is the sensor threshold data which defines severely degraded status
	status at the upper end of the range that impacts the functional status 
	of the sensor."
        INDEX   { saHpiDomainID, saHpiResourceID, saHpiSensorIndex }
        ::= {saHpiSensorThdUpMajorTable 1}

SaHpiSensorThdUpMajorEntry ::= SEQUENCE {
	saHpiSensorThdUpMajorIsReadable		TruthValue,
	saHpiSensorThdUpMajorIsWritable		TruthValue,
	saHpiSensorThdUpMajorIsFixed		TruthValue,
	saHpiSensorThdUpMajorValuesPresent	INTEGER,
	saHpiSensorThdUpMajorRaw		Unsigned32,
	saHpiSensorThdUpMajorInterpreted	OCTET STRING
	}


saHpiSensorThdUpMajorIsReadable	OBJECT-TYPE
	SYNTAX		TruthValue
	MAX-ACCESS	read-only
	STATUS		current
	DESCRIPTION
	"Defines if sensor threshold information can be read. 
	If set to 'false(2)' the saHpiSensorThdUpMajorRaw is set to
	'-1' and saHpiSensorThdUpMajorInterpreted is set to zero-length
	string."
	REFERENCE
	"Object derieved from SAF SAI-HPI-A.01.01 spec page 90 and 91."
	::= {saHpiSensorThdUpMajorEntry 1}

saHpiSensorThdUpMajorIsWritable	OBJECT-TYPE
	SYNTAX		TruthValue
	MAX-ACCESS	read-only
	STATUS		current
	DESCRIPTION
	"Defines if sensor threshold information can be written to. 

	If set to 'false(2)' writting to saHpiSensorThdUpMajorRaw 
	and saHpiSensorThdUpMajorInterpreted will not change the
	threshold values."
	REFERENCE
	"Object derieved from SAF SAI-HPI-A.01.01 spec page 90 and 91."
	::= {saHpiSensorThdUpMajorEntry 2}

saHpiSensorThdUpMajorIsFixed	OBJECT-TYPE
	SYNTAX		TruthValue
	MAX-ACCESS	read-only
	STATUS		current
	DESCRIPTION
	"Defines if sensor threshold information is fixed - cannot be changed.

	If set to 'false(2)' writting to saHpiSensorThdUpMajorRaw 
	and saHpiSensorThdUpMajorInterpreted will not change the
	threshold values."
	REFERENCE
	"Object derieved from SAF SAI-HPI-A.01.01 spec page 90 and 91."
	::= {saHpiSensorThdUpMajorEntry 3}

saHpiSensorThdUpMajorValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdUpMajorEntry 4}

saHpiSensorThdUpMajorRaw OBJECT-TYPE
        SYNTAX          Unsigned32
        MAX-ACCESS      read-write
        STATUS          current
        DESCRIPTION     
	"The raw (as unsigned 32 bit value) value which defines the severely
	degraded status at upper end of the range that impacts the functional 
	status of the sensor.

	Note:
	If 'saHpiSensorThdUpMajorIsReadable' is set to 'true(1)', this value
	can be read. Otherwise the value is set to '-1'.

	If 'saHpiSensorThdUpMajorisWriteable' is set to 'true(1)', this value
	can be changed. Otherwise this value can not be modified.
	After the write operation the value of interpreted object will change
	accordingly.
	
	Finally, if 'saHpiSensorThdUpMajorIsFixed' objects is set to 'true(1)',
	this value can not be changed.
	"
        ::= {saHpiSensorThdUpMajorEntry 5}

saHpiSensorThdUpMajorInterpreted OBJECT-TYPE
	SYNTAX		OCTET STRING(SIZE(0..255))
	MAX-ACCESS	read-write
	STATUS		current
	DESCRIPTION
	"Interpreted threshold value which defines the severely degraded
	status at the upper end of the range that impacts the functional status 
	of the sensor.

	Example of this is:

		'32.6F'
		'1900.33 rpm'
		'39 newton over cuM'
		'23123198918392.239998 gram over cuCm'
	"
	REFERENCE
	"Object derieved from SAF SAI-HPI-A.01.01 spec page 87."
	::= {saHpiSensorThdUpMajorEntry 6}


saHpiSensorThdUpMinorTable OBJECT-TYPE
        SYNTAX          SEQUENCE OF SaHpiSensorThdUpMinorEntry
        MAX-ACCESS      not-accessible
        STATUS          current
        DESCRIPTION     "A table definining  degraded status at the
	upper end of critical threshold values for sensor that supports raw or 
	interpreted values."
        ::= {hpiSensor 12}

saHpiSensorThdUpMinorEntry OBJECT-TYPE
	SYNTAX		SaHpiSensorThdUpMinorEntry
        MAX-ACCESS      not-accessible
        STATUS          current
        DESCRIPTION
	"This is the sensor threshold data which defines  degraded status
	status at the upper end of the range that impacts the functional status 
	of the sensor."
        INDEX   { saHpiDomainID, saHpiResourceID, saHpiSensorIndex }
        ::= {saHpiSensorThdUpMinorTable 1}

SaHpiSensorThdUpMinorEntry ::= SEQUENCE {
	saHpiSensorThdUpMinorIsReadable		TruthValue,
	saHpiSensorThdUpMinorIsWritable		TruthValue,
	saHpiSensorThdUpMinorIsFixed			TruthValue,
	saHpiSensorThdUpMinorValuesPresent		INTEGER,
	saHpiSensorThdUpMinorRaw			Unsigned32,
	saHpiSensorThdUpMinorInterpreted		OCTET STRING
	}


saHpiSensorThdUpMinorIsReadable	OBJECT-TYPE
	SYNTAX		TruthValue
	MAX-ACCESS	read-only
	STATUS		current
	DESCRIPTION
	"Defines if sensor threshold information can be read. 
	If set to 'false(2)' the saHpiSensorThdUpMinorRaw is set to
	'-1' and saHpiSensorThdUpMinorInterpreted is set to zero-length
	string."
	REFERENCE
	"Object derieved from SAF SAI-HPI-A.01.01 spec page 90 and 91."
	::= {saHpiSensorThdUpMinorEntry 1}

saHpiSensorThdUpMinorIsWritable	OBJECT-TYPE
	SYNTAX		TruthValue
	MAX-ACCESS	read-only
	STATUS		current
	DESCRIPTION
	"Defines if sensor threshold information can be written to. 

	If set to 'false(2)' writting to saHpiSensorThdUpMinorRaw 
	and saHpiSensorThdUpMinorInterpreted will not change the
	threshold values."
	REFERENCE
	"Object derieved from SAF SAI-HPI-A.01.01 spec page 90 and 91."
	::= {saHpiSensorThdUpMinorEntry 2}

saHpiSensorThdUpMinorIsFixed	OBJECT-TYPE
	SYNTAX		TruthValue
	MAX-ACCESS	read-only
	STATUS		current
	DESCRIPTION
	"Defines if sensor threshold information is fixed - cannot be changed.

	If set to 'false(2)' writting to saHpiSensorThdUpMinorRaw 
	and saHpiSensorThdUpMinorInterpreted will not change the
	threshold values."
	REFERENCE
	"Object derieved from SAF SAI-HPI-A.01.01 spec page 90 and 91."
	::= {saHpiSensorThdUpMinorEntry 3}

saHpiSensorThdUpMinorValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdUpMinorEntry 4}

saHpiSensorThdUpMinorRaw OBJECT-TYPE
        SYNTAX          Unsigned32
        MAX-ACCESS      read-write
        STATUS          current
        DESCRIPTION     
	"The raw (as unsigned 32 bit value) value which defines the 
	degraded status at upper end of the range that impacts the functional 
	status of the sensor.

	Note:
	If 'saHpiSensorThdUpMinorIsReadable' is set to 'true(1)', this value
	can be read. Otherwise the value is set to '-1'.

	If 'saHpiSensorThdUpMinorisWriteable' is set to 'true(1)', this value
	can be changed. Otherwise this value can not be modified.
	After the write operation the value of interpreted object will change
	accordingly.
	
	Finally, if 'saHpiSensorThdUpMinorIsFixed' objects is set to 'true(1)',
	this value can not be changed.
	"
        ::= {saHpiSensorThdUpMinorEntry 5}

saHpiSensorThdUpMinorInterpreted OBJECT-TYPE
	SYNTAX		OCTET STRING(SIZE(0..255))
	MAX-ACCESS	read-write
	STATUS		current
	DESCRIPTION
	"Interpreted threshold value which defines the  degraded
	status at the upper end of the range that impacts the functional status 
	of the sensor.

	Example of this is:

		'32.6F'
		'1900.33 rpm'
		'39 newton over cuM'
		'23123198918392.239998 gram over cuCm'
	"
	REFERENCE
	"Object derieved from SAF SAI-HPI-A.01.01 spec page 87."
	::= {saHpiSensorThdUpMinorEntry 6}





saHpiSensorThdPosHysteresisTable OBJECT-TYPE
        SYNTAX          SEQUENCE OF SaHpiSensorThdPosHysteresisEntry
        MAX-ACCESS      not-accessible
        STATUS          current
        DESCRIPTION     "A table definining hysteresis status at the
	positive range over a range which a change is accepted in a 
	sensor that supports raw or interpreted values."
        ::= {hpiSensor 13}

saHpiSensorThdPosHysteresisEntry OBJECT-TYPE
	SYNTAX		SaHpiSensorThdPosHysteresisEntry
        MAX-ACCESS      not-accessible
        STATUS          current
        DESCRIPTION
	"This is the sensor threshold data which defines hysteresis values
	at the positive range over a range which a change is accepted in a
	sensor that supports raw or interpreted values."
        INDEX   { saHpiDomainID, saHpiResourceID, saHpiSensorIndex }
        ::= {saHpiSensorThdPosHysteresisTable 1}

SaHpiSensorThdPosHysteresisEntry ::= SEQUENCE {
	saHpiSensorThdPosHysteresisIsReadable		TruthValue,
	saHpiSensorThdPosHysteresisIsWritable		TruthValue,
	saHpiSensorThdPosHysteresisIsFixed		TruthValue,
	saHpiSensorThdPosHysteresisValuesPresent	INTEGER,
	saHpiSensorThdPosHysteresisRaw			Unsigned32,
	saHpiSensorThdPosHysteresisInterpreted		OCTET STRING
	}


saHpiSensorThdPosHysteresisIsReadable	OBJECT-TYPE
	SYNTAX		TruthValue
	MAX-ACCESS	read-only
	STATUS		current
	DESCRIPTION
	"Defines if sensor threshold information can be read. 
	If set to 'false(2)' the saHpiSensorThdPosHysteresisRaw is set to
	'-1' and saHpiSensorThdPosHysteresisInterpreted is set to zero-length
	string."
	REFERENCE
	"Object derieved from SAF SAI-HPI-A.01.01 spec page 90 and 91."
	::= {saHpiSensorThdPosHysteresisEntry 1}

saHpiSensorThdPosHysteresisIsWritable	OBJECT-TYPE
	SYNTAX		TruthValue
	MAX-ACCESS	read-only
	STATUS		current
	DESCRIPTION
	"Defines if sensor threshold information can be written to. 

	If set to 'false(2)' writting to saHpiSensorThdPosHysteresisRaw 
	and saHpiSensorThdPosHysteresisInterpreted will not change the
	threshold values."
	REFERENCE
	"Object derieved from SAF SAI-HPI-A.01.01 spec page 90 and 91."
	::= {saHpiSensorThdPosHysteresisEntry 2}

saHpiSensorThdPosHysteresisIsFixed	OBJECT-TYPE
	SYNTAX		TruthValue
	MAX-ACCESS	read-only
	STATUS		current
	DESCRIPTION
	"Defines if sensor threshold information is fixed - cannot be changed.

	If set to 'false(2)' writting to saHpiSensorThdPosHysteresisRaw 
	and saHpiSensorThdPosHysteresisInterpreted will not change the
	threshold values."
	REFERENCE
	"Object derieved from SAF SAI-HPI-A.01.01 spec page 90 and 91."
	::= {saHpiSensorThdPosHysteresisEntry 3}

saHpiSensorThdPosHysteresisValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdPosHysteresisEntry 4}

saHpiSensorThdPosHysteresisRaw OBJECT-TYPE
        SYNTAX          Unsigned32
        MAX-ACCESS      read-write
        STATUS          current
        DESCRIPTION     
	"The raw (as unsigned 32 bit value) value which defines the 
	positive hysteresis over the range in which a change is accepted.

	Note:
	If 'saHpiSensorThdPosHysteresisIsReadable' is set to 'true(1)', this value
	can be read. Otherwise the value is set to '-1'.

	If 'saHpiSensorThdPosHysteresisisWriteable' is set to 'true(1)', this value
	can be changed. Otherwise this value can not be modified.
	After the write operation the value of interpreted object will change
	accordingly.
	
	Finally, if 'saHpiSensorThdPosHysteresisIsFixed' objects is set to 'true(1)',
	this value can not be changed.
	"
        ::= {saHpiSensorThdPosHysteresisEntry 5}

saHpiSensorThdPosHysteresisInterpreted OBJECT-TYPE
	SYNTAX		OCTET STRING(SIZE(0..255))
	MAX-ACCESS	read-write
	STATUS		current
	DESCRIPTION
	"Interpreted threshold value which defines the 
	positive hysteresis over the range in which a change is accepted.

	Example of this is:

		'32.6F'
		'1900.33 rpm'
		'39 newton over cuM'
		'23123198918392.239998 gram over cuCm'
	"
	REFERENCE
	"Object derieved from SAF SAI-HPI-A.01.01 spec page 87."
	::= {saHpiSensorThdPosHysteresisEntry 6}


saHpiSensorThdNegHysteresisTable OBJECT-TYPE
        SYNTAX          SEQUENCE OF SaHpiSensorThdNegHysteresisEntry
        MAX-ACCESS      not-accessible
        STATUS          current
        DESCRIPTION     "A table definining hysteresis values at the
	negative range over a range which a change is accepted in a 
	sensor that supports raw or interpreted values."
        ::= {hpiSensor 14}

saHpiSensorThdNegHysteresisEntry OBJECT-TYPE
	SYNTAX		SaHpiSensorThdNegHysteresisEntry
        MAX-ACCESS      not-accessible
        STATUS          current
        DESCRIPTION
	"This is the sensor threshold data which defines hysteresis values
	at the negativie range over a range which a change is accepted in a
	sensor that supports raw or interpreted values."
        INDEX   { saHpiDomainID, saHpiResourceID, saHpiSensorIndex }
        ::= {saHpiSensorThdNegHysteresisTable 1}

SaHpiSensorThdNegHysteresisEntry ::= SEQUENCE {
	saHpiSensorThdNegHysteresisIsReadable		TruthValue,
	saHpiSensorThdNegHysteresisIsWritable		TruthValue,
	saHpiSensorThdNegHysteresisIsFixed		TruthValue,
	saHpiSensorThdNegHysteresisValuesPresent	INTEGER,
	saHpiSensorThdNegHysteresisRaw			Unsigned32,
	saHpiSensorThdNegHysteresisInterpreted		OCTET STRING
	}


saHpiSensorThdNegHysteresisIsReadable	OBJECT-TYPE
	SYNTAX		TruthValue
	MAX-ACCESS	read-only
	STATUS		current
	DESCRIPTION
	"Defines if sensor threshold information can be read. 
	If set to 'false(2)' the saHpiSensorThdNegHysteresisRaw is set to
	'-1' and saHpiSensorThdNegHysteresisInterpreted is set to zero-length
	string."
	REFERENCE
	"Object derieved from SAF SAI-HPI-A.01.01 spec page 90 and 91."
	::= {saHpiSensorThdNegHysteresisEntry 1}

saHpiSensorThdNegHysteresisIsWritable	OBJECT-TYPE
	SYNTAX		TruthValue
	MAX-ACCESS	read-only
	STATUS		current
	DESCRIPTION
	"Defines if sensor threshold information can be written to. 

	If set to 'false(2)' writting to saHpiSensorThdNegHysteresisRaw 
	and saHpiSensorThdNegHysteresisInterpreted will not change the
	threshold values."
	REFERENCE
	"Object derieved from SAF SAI-HPI-A.01.01 spec page 90 and 91."
	::= {saHpiSensorThdNegHysteresisEntry 2}

saHpiSensorThdNegHysteresisIsFixed	OBJECT-TYPE
	SYNTAX		TruthValue
	MAX-ACCESS	read-only
	STATUS		current
	DESCRIPTION
	"Defines if sensor threshold information is fixed - cannot be changed.

	If set to 'false(2)' writting to saHpiSensorThdNegHysteresisRaw 
	and saHpiSensorThdNegHysteresisInterpreted will not change the
	threshold values."
	REFERENCE
	"Object derieved from SAF SAI-HPI-A.01.01 spec page 90 and 91."
	::= {saHpiSensorThdNegHysteresisEntry 3}

saHpiSensorThdNegHysteresisValuesPresent OBJECT-TYPE
	SYNTAX		INTEGER {
				undefined(0),
				raw(2),
				interpreted(3),
				rawAndInterpreted(4)
			}
	MAX-ACCESS	read-only
	STATUS		current
	DESCRIPTION
	"Each sensor may support threshold information in
	raw or interpreted representations of the sensor."
	REFERENCE
	"Object derieved from SAF SAI-HPI-A.01.01 spec page 90 and 91."
	::= {saHpiSensorThdNegHysteresisEntry 4}

saHpiSensorThdNegHysteresisRaw OBJECT-TYPE
        SYNTAX          Unsigned32
        MAX-ACCESS      read-write
        STATUS          current
        DESCRIPTION     
	"The raw (as unsigned 32 bit value) value which defines the
	negative hysteresis over the range in which a change is accepted.

	Note:
	If 'saHpiSensorThdNegHysteresisIsReadable' is set to 'true(1)', this value
	can be read. Otherwise the value is set to '-1'.

	If 'saHpiSensorThdNegHysteresisisWriteable' is set to 'true(1)', this value
	can be changed. Otherwise this value can not be modified.
	After the write operation the value of interpreted object will change
	accordingly.
	
	Finally, if 'saHpiSensorThdNegHysteresisIsFixed' objects is set to 'true(1)',
	this value can not be changed.
	"
        ::= {saHpiSensorThdNegHysteresisEntry 5}

saHpiSensorThdNegHysteresisInterpreted OBJECT-TYPE
	SYNTAX		OCTET STRING(SIZE(0..255))
	MAX-ACCESS	read-write
	STATUS		current
	DESCRIPTION
	"Interpreted threshold value which defines the negative hysteresis
	over the range in which a change is accepted.

	Example of this is:

		'32.6F'
		'1900.33 rpm'
		'39 newton over cuM'
		'23123198918392.239998 gram over cuCm'
	"
	REFERENCE
	"Object derieved from SAF SAI-HPI-A.01.01 spec page 87."
	::= {saHpiSensorThdNegHysteresisEntry 6}

--
-- /*******************************************************************************
-- ********************************************************************************
-- **********                                                            **********
-- **********                    Entity Inventory Data                   **********
-- **********                                                            **********
-- ********************************************************************************
-- *******************************************************************************/

		
saHpiInventoryCount OBJECT-TYPE
	SYNTAX		Counter32
	MAX-ACCESS	read-only
	STATUS		current
	DESCRIPTION	"The number of inventory resource data records present on this system."
	::= {hpiResources 8}

saHpiInventoryTable OBJECT-TYPE
	SYNTAX		SEQUENCE OF SaHpiInventoryEntry
	MAX-ACCESS	not-accessible
	STATUS		current
	DESCRIPTION	"Table defining entity inventory resource data records."
	::= {hpiResources 9}
saHpiInventoryEntry OBJECT-TYPE
	SYNTAX		SaHpiInventoryEntry
	MAX-ACCESS	not-accessible
	STATUS		current
	DESCRIPTION
		"These structures are used to read and write inventory data to entity inventory
		repositories within a resource."
	INDEX	{ saHpiDomainID, saHpiResourceID, saHpiInventoryEirId, saHpiInventoryIndex }
	::= {saHpiInventoryTable 1}


SaHpiInventoryEntry ::= SEQUENCE {
	saHpiInventoryEirId		Unsigned32,
	saHpiInventoryIndex		Unsigned32,
	saHpiInventoryRecordType	INTEGER,
	saHpiInventoryValidity		INTEGER,
	saHpiInventoryAttributes	OCTET STRING,
	saHpiInventoryTextType		INTEGER,
	saHpiInventoryTextLanguage	INTEGER,
	saHpiInventoryManufacturer	OCTET STRING,
	saHpiInventoryProductName	OCTET STRING,
	saHpiInventoryProductVersion	OCTET STRING,
	saHpiInventoryModelNumber	OCTET STRING,
	saHpiInventorySerialNumber	OCTET STRING,
	saHpiInventoryPartNumber	OCTET STRING,
	saHpiInventoryFileId		OCTET STRING,
	saHpiInventoryAssetTag		OCTET STRING,
	saHpiInventoryCustomField	OCTET STRING,
	saHpiInventoryOEM		Unsigned32,
	saHpiInventoryRDR		RowPointer
	}

saHpiInventoryEirId OBJECT-TYPE
        SYNTAX          Unsigned32
        MAX-ACCESS      read-only
        STATUS          current
        DESCRIPTION     
	"Identifier for an entity inventory repository. The  default is
	SAHPI_DEFAULT_INVENTORY_ID  0x00 "
        ::= {saHpiInventoryEntry 1}

saHpiInventoryIndex OBJECT-TYPE
	SYNTAX		Unsigned32
	MAX-ACCESS	read-only
	STATUS		current
	DESCRIPTION	"Sub-index for the inventory data resource record.
	This value enumerate n-inventory data resource records for
	a record that has mulitple inventory entires (for the same 
	saHpiInventoryEirId)."
	::= {saHpiInventoryEntry 2}

saHpiInventoryRecordType OBJECT-TYPE
        SYNTAX          INTEGER {
				undefined (0),
				internalUse(177),
                                chassisInfo(178),
                                boardInfo(179),
                                productInfo(180),
                                oem(193)
			}
        MAX-ACCESS      read-only
        STATUS          current
        DESCRIPTION     " Inventory Record definitions"
        ::= {saHpiInventoryEntry 3}

saHpiInventoryValidity OBJECT-TYPE
        SYNTAX          INTEGER{
				undefined (0),
				valid(1),
				invalid(2),
				dataOverflow(3)
			}
        MAX-ACCESS      read-only
        STATUS          current
        DESCRIPTION     "Indication as to whether data is complete and valid. "
        ::= {saHpiInventoryEntry 4}

saHpiInventoryAttributes OBJECT-TYPE
	SYNTAX		OCTET STRING (SIZE(8|12|260|1000))
	MAX-ACCESS	read-write
	STATUS		current
	DESCRIPTION	
  	"This attribute represents the current setting of the inventory.  It must
         be interpreted in the context of saHpiInventoryRecordType.

        internalUse  - Variable length opaque data. Max length
		       of data is 1000 octets. 

        chassisInfo  - Chassis informations are represented as follows:
		octet 1-4		- determines the type of chassis:

				other (2), unknown (3), desktop (4),
				lowProfileDesktop (5), pizzaBox (6),
				miniTower (7), tower (8), portable (9),
				laptop (10), notebook (11), handheld (12),
				dockingStation (13), allinone (14),
				subnotebook (15), spaceSaving (16),
				lunchBox (17), mainServer (18),
				expansion (19), subchassis (20),
				busExpansionChassis (21),
				peripheralChassis (22), raidChassis (23),
				rackmount (24)
		octet 4-12	- manufacturing date/time represented
			as 64-bit signed integer from 00:00:00, 
			January 1, 1970, in a 64-bit signed integer. This format
			is sufficient to represent times with nano-second resolution from the
			year 1678 to 2262.
			
			The value -263, which is 0x8000000000000000, is used to indicate
			unknownunspecified time.

		The rest of information is provided in following objects

		saHpiInventoryManufacturer
		saHpiInventoryProductName
		saHpiInventoryProductVersion
		saHpiInventoryModelNumber
		saHpiInventorySerialNumber
		saHpiInventoryPartNumber
		saHpiInventoryFileId
		saHpiInventoryAssetTag
		saHpiInventoryCustomField
			 			
	boardInfo- Textual information regarding the board.
		octet 1-8	- manufacturing date/time represented
			as 64-bit signed integer from 00:00:00, 
			January 1, 1970, in a 64-bit signed integer. This format
			is sufficient to represent times with nano-second resolution from the
			year 1678 to 2262.
			
			The value -263, which is 0x8000000000000000, is used to indicate
			unknownunspecified time.

		The rest of information is provided in following objects

		saHpiInventoryManufacturer
		saHpiInventoryProductName
		saHpiInventoryProductVersion
		saHpiInventoryModelNumber
		saHpiInventorySerialNumber
		saHpiInventoryPartNumber
		saHpiInventoryFileId
		saHpiInventoryAssetTag
		saHpiInventoryCustomField	 
              

		   
	productInfo-The information of the product board represented as follows:

		octet 1-8	- manufacturing date/time represented
			as 64-bit signed integer from 00:00:00, 
			January 1, 1970, in a 64-bit signed integer. This format
			is sufficient to represent times with nano-second resolution from the
			year 1678 to 2262.
			
			The value -263, which is 0x8000000000000000, is used to indicate
			unknownunspecified time.

		The rest of information is provided in following objects

		saHpiInventoryManufacturer
		saHpiInventoryProductName
		saHpiInventoryProductVersion
		saHpiInventoryModelNumber
		saHpiInventorySerialNumber
		saHpiInventoryPartNumber
		saHpiInventoryFileId
		saHpiInventoryAssetTag
		saHpiInventoryCustomField
			                 

	oem	- OEM data represented as follows:
		octet 1-4	- manufacturer ID in network byte order 
		octet 5-n	- variable length data (defined by OEM).
				  max(n) is 260."
        ::= {saHpiInventoryEntry 5}

saHpiInventoryTextType OBJECT-TYPE 
	SYNTAX		INTEGER {
				undefined(0),
				binary(1), 
				bcdplus(2), 
				ascii6(3),
				language(4)
			}
	MAX-ACCESS	read-write
	STATUS		current
	DESCRIPTION	"Defines the type of data the saHpiResourceTag is
	encoded as:
	 binary(1):
		  String of bytes, any values legal

         bcdplus(2)
		String of 0-9, space, dash, period ONLY

         ascii6(3)
		Reduced ASCII character set: 0x20-0x5F ONLY

         language(4)
		ASCII or UNICODE depending on language
	"
	::= {saHpiInventoryEntry 6}

saHpiInventoryTextLanguage OBJECT-TYPE
	SYNTAX		INTEGER {
				undefined (0),
				unknown (1),
				afar (2),
				abkhazian (3),
				afrikaans (4),
				amharic (5),
				arabic (6),
				assamese (7),
				aymara (8),
				azerbaijani (9),
				bashkir (10),
				byelorussian (11),
				bulgarian (12),
				bihari (13),
				bislama (14),
				bengali (15),
				tibetan (16),
				breton (17),
				catalan (18),
				corsican (19),
				czech (20),
				welsh (21),
				danish (22),
				german (23),
				bhutani (24),
				greek (25),
				english (26),
				esperanto (27),
				spanish (28),
				estonian (29),
				basque (30),
				persian (31),
				finnish (32),
				fiji (33),
				faeroese (34),
				french (35),
				frisian (36),
				irish (37),
				scotsgaelic (38),
				galician (39),
				guarani (40),
				gujarati (41),
				hausa (42),
				hindi (43),
				croatian (44),
				hungarian (45),
				armenian (46),
				interlingua (47),
				interlingue (48),
				inupiak (49),
				indonesian (50),
				icelandic (51),
				italian (52),
				hebrew (53),
				japanese (54),
				yiddish (55),
				javanese (56),
				georgian (57),
				kazakh (58),
				greenlandic (59),
				cambodian (60),
				kannada (61),
				korean (62),
				kashmiri (63),
				kurdish (64),
				kirghiz (65),
				latin (66),
				lingala (67),
				laothian (68),
				lithuanian (69),
				latvianlettish (70),
				malagasy (71),
				maori (72),
				macedonian (73),
				malayalam (74),
				mongolian (75),
				moldavian (76),
				marathi (77),
				malay (78),
				maltese (79),
				burmese (80),
				nauru (81),
				nepali (82),
				dutch (83),
				norwegian (84),
				occitan (85),
				afanoromo (86),
				oriya (87),
				punjabi (88),
				polish (89),
				pashtopushto (90),
				portuguese (91),
				quechua (92),
				rhaetoromance (93),
				kirundi (94),
				romanian (95),
				russian (96),
				kinyarwanda (97),
				sanskrit (98),
				sindhi (99),
				sangro (100),
				serbocroatian (101),
				singhalese (102),
				slovak (103),
				slovenian (104),
				samoan (105),
				shona (106),
				somali (107),
				albanian (108),
				serbian (109),
				siswati (110),
				sesotho (111),
				sudanese (112),
				swedish (113),
				swahili (114),
				tamil (115),
				telugu (116),
				tajik (117),
				thai (118),
				tigrinya (119),
				turkmen (120),
				tagalog (121),
				setswana (122),
				tonga (123),
				turkish (124),
				tsonga (125),
				tatar (126),
				twi (127),
				ukrainian (128),
				urdu (129),
				uzbek (130),
				vietnamese (131),
				volapuk (132),
				wolof (133),
				xhosa (134),
				yoruba (135),
				chinese (136),
				zulu (137)
			}
        MAX-ACCESS      read-write
	STATUS          current
	DESCRIPTION     "
	This enumeration lists all of the languages that can be 
	associated with text.  Undef (0) indicates that 
	the language is unspecified or unknown.  "
	::= {saHpiInventoryEntry 7}

saHpiInventoryManufacturer OBJECT-TYPE
        SYNTAX          OCTET STRING(SIZE(0..255))
        MAX-ACCESS      read-write
        STATUS          current
        DESCRIPTION     "
	Manufacturer  of the inventory resource data record product.
	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 8}

saHpiInventoryProductName OBJECT-TYPE
        SYNTAX          OCTET STRING(SIZE(0..255)) 
        MAX-ACCESS      read-write
        STATUS          current
        DESCRIPTION     "
	Product name of the inventory resource data record product.
	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 9}

saHpiInventoryProductVersion OBJECT-TYPE
        SYNTAX          OCTET STRING(SIZE(0..255))
        MAX-ACCESS      read-write
        STATUS          current
        DESCRIPTION     "
	Product version of the inventory resource data record product.
	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 10}

saHpiInventoryModelNumber OBJECT-TYPE
        SYNTAX          OCTET STRING(SIZE(0..255))
        MAX-ACCESS      read-write
        STATUS          current
        DESCRIPTION     "
	Model number of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 11}

saHpiInventorySerialNumber OBJECT-TYPE
        SYNTAX          OCTET STRING(SIZE(0..255))
        MAX-ACCESS      read-write
        STATUS          current
        DESCRIPTION     "
	Serial number of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 12}

saHpiInventoryPartNumber OBJECT-TYPE
        SYNTAX          OCTET STRING(SIZE(0..255))
        MAX-ACCESS      read-write
        STATUS          current
        DESCRIPTION     "
	Part number  of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 13}

saHpiInventoryFileId OBJECT-TYPE
        SYNTAX          OCTET STRING(SIZE(0..255))
        MAX-ACCESS      read-write
        STATUS          current
        DESCRIPTION     "
	File id of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 14}

saHpiInventoryAssetTag OBJECT-TYPE
        SYNTAX          OCTET STRING(SIZE(0..255))
        MAX-ACCESS      read-write
        STATUS          current
        DESCRIPTION     "
	Asset tag of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 15}

saHpiInventoryCustomField OBJECT-TYPE
        SYNTAX          OCTET STRING(SIZE(0..255))
        MAX-ACCESS      read-write
        STATUS          current
        DESCRIPTION     "
	Custom field of the inventory resource data record product.

	It must be interpreted in the context of saHpiInventoryRecordType to 
	figure out if this information is related to  chassisInfo(177),
        boardInfo(178), or oductInfo(179) of the inventory item.

	Zero-length description means that the device does NOT have the means
	to provide correct information (or simply the device not support 
	this entry).

	Changing this field in those cases may not alter the inventory 
	information."
        ::= {saHpiInventoryEntry 16}

saHpiInventoryOEM OBJECT-TYPE
	SYNTAX		Unsigned32
	MAX-ACCESS	read-only
	STATUS		current
	DESCRIPTION
	"OEM value for the inventory record. This is
	manufacturere' specific value."
	::= {saHpiInventoryEntry 17}

saHpiInventoryRDR OBJECT-TYPE
        SYNTAX          RowPointer
        MAX-ACCESS      read-only
        STATUS          current
        DESCRIPTION     "Pointer to resource data record for this particulat inventory resource data record"
        ::= {saHpiInventoryEntry 18}
--
-- /*******************************************************************************
-- ********************************************************************************
-- **********                                                            **********
-- **********                  Watchdog Resource Data Records            **********
-- **********                                                            **********
-- ********************************************************************************
-- *******************************************************************************/
--


saHpiWatchdogCount OBJECT-TYPE
	SYNTAX		Counter32
	MAX-ACCESS	read-only
	STATUS		current
	DESCRIPTION	"The number of watchdogs present on this system."
	::= {hpiResources 10}

saHpiWatchdogTable OBJECT-TYPE
        SYNTAX          SEQUENCE OF SaHpiWatchdogEntry
        MAX-ACCESS      not-accessible
        STATUS          current
        DESCRIPTION	"Table of watchdog  resource data records."
        ::= {hpiResources 11}

saHpiWatchdogEntry OBJECT-TYPE
        SYNTAX          SaHpiWatchdogEntry
        MAX-ACCESS      not-accessible
        STATUS          current
        DESCRIPTION     " When the 'Watchdog' capability is set in a resource, a watchdog with an
 identifier of SAHPI_DEFAULT_WATCHDOG_NUM is required. All watchdogs must be
 represented in the RDR repository with an saHpiWatchdogRecT, including the
 watchdog with an identifier of SAHPI_DEFAULT_WATCHDOG_NUM."
        INDEX   { saHpiDomainID, saHpiResourceID, saHpiWatchdogNum }
        ::= {saHpiWatchdogTable 1}

SaHpiWatchdogEntry ::= SEQUENCE {
	saHpiWatchdogNum		Unsigned32,
	saHpiWatchdogLog		TruthValue,
	saHpiWatchdogRunning		TruthValue,
	saHpiWatchdogTimerUse		INTEGER,
	saHpiWatchdogTimerAction	INTEGER,
	saHpiWatchdogPretimerInterrupt	INTEGER,
	saHpiWatchdogPreTimeoutInterval	Unsigned32,
	saHpiWatchdogTimerUseExpFlags	Unsigned32,
	saHpiWatchdogTimerInitialCount	Unsigned32,
	saHpiWatchdogTimerPresentCount	Unsigned32,
	saHpiWatchdogTimerReset		TruthValue,
	saHpiWatchdogOem		Unsigned32,
	saHpiWatchdogRDR		RowPointer
      }

saHpiWatchdogNum OBJECT-TYPE
        SYNTAX          Unsigned32
        MAX-ACCESS      read-only
        STATUS          current
        DESCRIPTION     "Watchdog number"
        ::= {saHpiWatchdogEntry 1}

 
saHpiWatchdogLog OBJECT-TYPE 
	SYNTAX		TruthValue
	MAX-ACCESS	read-write
	STATUS		current
	DESCRIPTION	"
	If you read this object, it means:
	Log -  indicates whether or not the Watchdog is configured to
               issue an event when it next times out. TRUE=event will
               be issued on timeout.
	If you set this object, it means:
	Log -  indicates whether or not the Watchdog should  issue
               an event when it next times out. TRUE=event will be
               issued on timeout.

	Setting this object will NOT take effect on the Watchdog until the
	object SaHpiWatchdogRunning is set to true(1).
	"
	::= {saHpiWatchdogEntry 2}

saHpiWatchdogRunning OBJECT-TYPE 
	SYNTAX		TruthValue
	MAX-ACCESS	read-write
	STATUS		current
	DESCRIPTION	"
	If you read this object, it means:
	Running -	indicates whether or not the Watchdog is currently
                        running or stopped. TRUE=Watchdog is running.
	If you set this object, it means:
	Running -	indicates whether or not the Watchdog should be
                        stopped before updating.
                        TRUE =  Watchdog is not stopped. If it is already
                                stopped, it will remain stopped, but if it is
                                running, it will continue to run, with the
                                countdown timer reset to the new InitialCount.
                                Note that there is a race condition possible
                                with this setting, so it should be used with
                                care.
                        FALSE = Watchdog is stopped. After this object 
				is set, a subsequent read on this object
				is required to start the timer.
	"
	::= {saHpiWatchdogEntry 3}

saHpiWatchdogTimerUse OBJECT-TYPE
        SYNTAX          INTEGER {
				undefined(0),
				none (1),
				biosFrb2 (2),
				biosPost (3),
				osLoad (4),
				smsOs (5),
				oem (6),
				unspecified (16)
			}
        MAX-ACCESS      read-write
        STATUS          current
        DESCRIPTION     "
	If you read this object, it means:
	TimerUse - indicates the current use of the timer; one of five
                   preset uses which was included on the last
                   SET object request, or through some
                   other implementation-dependent means to start the
                   Watchdog timer.  
	If you set this object, it means:
	TimerUse - indicates the current use of the timer. Will control
                   which saHpiWatchdogTimerUseExpFlags is set if the timer expires

	Setting this object will NOT take effect on the Watchdog until the
	object SaHpiWatchdogRunning is set to true(1)."
        ::= {saHpiWatchdogEntry 4}

saHpiWatchdogTimerAction OBJECT-TYPE
        SYNTAX          INTEGER {
				undefined(0),
				noAction (1),
				reset (2),
				powerDown (3),
				powerCycle (4)
			}
        MAX-ACCESS      read-write
        STATUS          current
        DESCRIPTION     
	"Indicates what action will be taken when the Watchdog times out.

	 Setting this object will NOT take effect on the Watchdog until the
	object SaHpiWatchdogRunning is set to true(1)."
        ::= {saHpiWatchdogEntry 5}

saHpiWatchdogPretimerInterrupt OBJECT-TYPE
        SYNTAX          INTEGER {
				undefined(0),
				none (1),
				smi (2),
				nmi (3),
				messageInterrupt (4),
				oem (16)
			}
        MAX-ACCESS      read-write
        STATUS          current
        DESCRIPTION     
	"PretimerInterrupt -  indicates which action will be taken
                        'PreTimeoutInterval' seconds prior to Watchdog timer
                        expiration. 

	Setting this object will NOT take effect on the Watchdog until the
	object SaHpiWatchdogRunning is set to true(1)."
        ::= {saHpiWatchdogEntry 6}

saHpiWatchdogPreTimeoutInterval OBJECT-TYPE
        SYNTAX          Unsigned32 
        MAX-ACCESS      read-write
        STATUS          current
        DESCRIPTION     
	"PreTimeoutInterval indicates how many  milliseconds prior to timer time
                        out the PretimerInterrupt action will be taken. If
                        'PreTimeoutInterval' = 0, the PretimerInterrupt action
                        will occur concurrently with 'TimerAction.' HPI
                        implementations may not be able to support millisecond
                        resolution and may have a maximum value restriction.
                        These restrictions should be documented by the
                        provider of the HPI interface. 

	Setting this object will NOT take effect on the Watchdog until the
	object SaHpiWatchdogRunning is set to true(1)."
        ::= {saHpiWatchdogEntry 7}

saHpiWatchdogTimerUseExpFlags OBJECT-TYPE
        SYNTAX          Unsigned32 (0..62)
        MAX-ACCESS      read-write
        STATUS          current
        DESCRIPTION     "set of five bit flags which indicate that a Watchdog
                        timer timeout has occurred while the corresponding
                        TimerUse value was set. Once set, these flags stay
                        set until specifically cleared with a
                        SET on this object, or by some other
                        implementation-dependent means.
	
	Bit flags are:

	SAHPI_WATCHDOG_EXP_BIOS_FRB2   0x02
 	SAHPI_WATCHDOG_EXP_BIOS_POST   0x04
 	SAHPI_WATCHDOG_EXP_OS_LOAD     0x08
 	SAHPI_WATCHDOG_EXP_SMS_OS      0x10
 	SAHPI_WATCHDOG_EXP_OEM         0x20

	The bit flag 0x00 indicates that this watchdog does not support
	any of the flags.

	Setting this object will NOT take effect on the Watchdog until the
	object SaHpiWatchdogRunning is set to true(1)."
        ::= {saHpiWatchdogEntry 8}

saHpiWatchdogTimerInitialCount OBJECT-TYPE
        SYNTAX          Unsigned32 
        MAX-ACCESS      read-write
        STATUS          current
        DESCRIPTION     "InitialCount -       The time, in milliseconds, 
			before the timer will time
                        out after a SaHpiWatchdogTimerReset() function call is
                        made, or some other implementation-dependent strobe is
                        sent to the Watchdog. HPI implementations may not be
                        able to support millisecond resolution and may have a
                        maximum value restriction. These restrictions should
                        be documented by the provider of the HPI interface.

	Setting this object will NOT take effect on the Watchdog until the
	object SaHpiWatchdogRunning is set to true(1)."
        ::= {saHpiWatchdogEntry 9}

saHpiWatchdogTimerPresentCount OBJECT-TYPE
        SYNTAX          Unsigned32 
        MAX-ACCESS      read-write
        STATUS          current
        DESCRIPTION     "PresentCount -       The remaining time in milliseconds before the timer
                        will time out unless a SaHpiWatchdogTimerReset()
                        function call is made, or some other implementation-
                        dependent strobe is sent to the Watchdog.
                        HPI implementations may not be able to support
                        millisecond resolution on watchdog timers, but will
                        return the number of clock ticks remaining times the
                        number of milliseconds between each tick. 

	Setting this object will NOT take effect on the Watchdog until the
	object SaHpiWatchdogRunning is set to true(1)."
        ::= {saHpiWatchdogEntry 10}

saHpiWatchdogTimerReset OBJECT-TYPE
	SYNTAX		TruthValue
	MAX-ACCESS	read-write
	STATUS		current
	DESCRIPTION	"This object provides a method to start or restart
	the watchdog timer from the initial countdown value. 

	Setting this to true(1) will 'strobe' the counter and reset to
	the initial countdown value as specified in 
	saHpiWatchdogTimerInitialCount.

	Setting this object will NOT take effect on the Watchdog until the
	object SaHpiWatchdogRunning is set to true(1)."
	::= {saHpiWatchdogEntry 11}

saHpiWatchdogOem OBJECT-TYPE
        SYNTAX          Unsigned32 
        MAX-ACCESS      read-only
        STATUS          current
        DESCRIPTION     "Reserved for OEM use"
        ::= {saHpiWatchdogEntry 12}

saHpiWatchdogRDR OBJECT-TYPE
	SYNTAX		RowPointer
	MAX-ACCESS	read-only
	STATUS		current
	DESCRIPTION	"Forward pointer to the RDR OID."
	::= {saHpiWatchdogEntry 13}
-- 
-- Notifications
--

hpiNotifications OBJECT IDENTIFIER ::= { hpi 4 }


saHpiSensorNotification NOTIFICATION-TYPE
	OBJECTS {	
		saHpiDomainID,
		saHpiResourceID,
		saHpiEventIndex,
		saHpiEventSeverity,
		saHpiEventSensorCategory,
		saHpiEventSensorState,
		saHpiEventSensorNum,
		saHpiEventSensorType,
		saHpiEventSensorOptionalData,
		saHpiEventSensorTriggerReadingRaw,
		saHpiEventSensorOem
	}
	STATUS current
 	DESCRIPTION
	"Sensor event notification."
	REFERENCE 
	"Derived from typedefs in SAI-HPI-A.01.01 pages 101, 102."
	::= { hpiNotifications 1 }

saHpiHotSwapNotification NOTIFICATION-TYPE
	OBJECTS {
		saHpiDomainID,
		saHpiResourceID,
		saHpiEventIndex,
		saHpiEventSeverity,
		saHpiEventHotSwapState,
		saHpiEventPreviousHotSwapState
	}
	STATUS current
	DESCRIPTION
	"Hot swap notification."
	::= { hpiNotifications 2}

saHpiWatchdogNotification NOTIFICATION-TYPE
	OBJECTS {
		saHpiDomainID,
		saHpiResourceID,
		saHpiEventIndex,
		saHpiEventSeverity,
		saHpiEventWatchdogNum,
		saHpiEventWatchdogAction,
		saHpiEventWatchdogPreTimerAction,
		saHpiEventWatchdogUse
	}
	STATUS current
	DESCRIPTION
	"Watchdog notification."
	::= { hpiNotifications 3}

saHpiOEMNotifications NOTIFICATION-TYPE
	OBJECTS {
		saHpiDomainID,
		saHpiResourceID,
		saHpiEventIndex,
		saHpiEventSeverity,
		saHpiEventOemManufacturerIdT,
		saHpiEventOemEventData
	}
	STATUS current
	DESCRIPTION
	"OEM event notifications."
	::= { hpiNotifications 4}

saHpiUserNotifications NOTIFICATION-TYPE
	OBJECTS {
		saHpiDomainID,
		saHpiResourceID,
		saHpiEventIndex,
		saHpiEventSeverity,
		saHpiEventUserEventData
	}
	STATUS current
	DESCRIPTION
	"User event notifications."
	::= { hpiNotifications 5}

saHpiResourceNotifications NOTIFICATION-TYPE
	OBJECTS {
		saHpiDomainID,
		saHpiResourceID,
		saHpiEntryID,
		saHpiResourceEntityPath,
		saHpiResourceCapabilities,
		saHpiResourceSeverity,
		saHpiEntryCount,
		saHpiEntryUpdateCount
	}
	STATUS current
	DESCRIPTION
	"Resource (RPT) change event notifications."
	::= { hpiNotifications 6}

saHpiResourceDataRecordNotifications NOTIFICATION-TYPE
	OBJECTS {
		saHpiDomainID,
		saHpiResourceID,
		saHpiRdrRecordId,
		saHpiRdrType,
		saHpiRdrEntityPath,
		saHpiRdr,
		saHpiRdrRTP,
		saHpiRdrCount
	}
	STATUS current
	DESCRIPTION
	"Resource  Data Record change event notifications."
	::= { hpiNotifications 7}

-- ---- ---- ---- ---- ---- ---- ---- ---- ---- ---- ---- ----       
--      OBJECT GROUP DECLARATIONS AND COMPLIANCE FOR SMIv2
-- ---- ---- ---- ---- ---- ---- ---- ---- ---- ---- ---- ----

hpiMIBCompliances OBJECT IDENTIFIER ::= { hpi 5 }

saHpiEntityGroup OBJECT-GROUP
	OBJECTS {
		saHpiEntryCount,
		saHpiEntryUpdateCount,
		saHpiEntryUpdateTimestamp,
		saHpiDomainID ,
		saHpiEntryID ,
		saHpiResourceID ,
		saHpiResourceEntityPath ,
		saHpiResourceCapabilities ,
		saHpiResourceSeverity ,
		saHpiResourceInfoResourceRev ,
		saHpiResourceInfoSpecificVer ,
		saHpiResourceInfoDeviceSupport ,
		saHpiResourceInfoManufacturerId ,
		saHpiResourceInfoProductId ,
		saHpiResourceInfoFirmwareMajorRev ,
		saHpiResourceInfoFirmwareMinorRev ,
		saHpiResourceInfoAuxFirmwareRev ,
		saHpiResourceTagTextType ,
		saHpiResourceTagTextLanguage,
		saHpiResourceTag,
		saHpiParamControl,
		saHpiClearEvents,
		saHpiEventLogTime,
		saHpiEventLogState
	}
	STATUS current
	DESCRIPTION
		"Entity group"
	::=  { hpiMIBCompliances 1}

saHpiEventGroup OBJECT-GROUP
	OBJECTS {
		saHpiEventCount,
		saHpiEventIndex,
		saHpiEventType,
		saHpiEventTimestamp,
		saHpiEventSeverity,
		saHpiEventSensorNum,
		saHpiEventSensorType,
		saHpiEventSensorCategory,
		saHpiEventSensorAssertion,
		saHpiEventSensorState,
		saHpiEventSensorOptionalData,
		saHpiEventSensorTriggerReadingType,
		saHpiEventSensorTriggerReadingRaw,
		saHpiEventSensorTriggerReadingInterpreted,
		saHpiEventSensorTriggerReadingEventStateFlag,
		saHpiEventSensorTriggerReadingEventState,
		saHpiEventSensorTriggerThresholdType,
		saHpiEventSensorTriggerThresholdRaw,
		saHpiEventSensorTriggerThresholdInterpreted,
		saHpiEventSensorTriggerThresholdEventStateFlag,
		saHpiEventSensorTriggerThresholdEventState,
		saHpiEventSensorPreviousState,
		saHpiEventSensorOem,
		saHpiEventSensorSpecific,
		saHpiEventHotSwapState,
		saHpiEventPreviousHotSwapState,
		saHpiEventWatchdogNum,
		saHpiEventWatchdogAction,
		saHpiEventWatchdogPreTimerAction,
		saHpiEventWatchdogUse,
		saHpiEventOemManufacturerIdT,
		saHpiEventOemEventData,
		saHpiEventUserEventData,
		saHpiEventDelete
	}
	STATUS current
	DESCRIPTION
		"Event group"
	::= { hpiMIBCompliances 2}

saHpiSystemEventGroup OBJECT-GROUP
	OBJECTS {
		saHpiSystemEventLogEntries,
		saHpiSystemEventLogSize,
		saHpiSystemEventLogUpdateTimestamp,
		saHpiSystemEventLogCurrentTime,
		saHpiSystemEventLogEnabled,
		saHpiSystemEventLogOverflowFlag,
		saHpiSystemEventLogOverflowAction,
		saHpiSystemEventLogDeleteEntrySupported,
		saHpiSystemEventLogIndex,
		saHpiSystemEventLogAddedTimestamp,
		saHpiSystemEventLogType,
		saHpiSystemEventLogTimestamp,
		saHpiSystemEventLogSeverity,
		saHpiSystemEventLogSensorNum,
		saHpiSystemEventLogSensorType,
		saHpiSystemEventLogSensorCategory,
		saHpiSystemEventLogSensorAssertion,
		saHpiSystemEventLogSensorState,
		saHpiSystemEventLogSensorOptionalData,
		saHpiSystemEventLogSensorTriggerReadingType,
		saHpiSystemEventLogSensorTriggerReadingRaw,
		saHpiSystemEventLogSensorTriggerReadingInterpreted,
		saHpiSystemEventLogSensorTriggerReadingEventStateFlag,
		saHpiSystemEventLogSensorTriggerReadingEventState,
		saHpiSystemEventLogSensorTriggerThresholdRaw,
		saHpiSystemEventLogSensorTriggerThresholdInterpreted,
		saHpiSystemEventLogSensorTriggerThresholdEventStateFlag,
		saHpiSystemEventLogSensorTriggerThresholdEventState,
		saHpiSystemEventLogSensorPreviousState,
		saHpiSystemEventLogSensorOem,
		saHpiSystemEventLogSensorSpecific,
		saHpiSystemEventLogHotSwapState,
		saHpiSystemEventLogPreviousHotSwapState,
		saHpiSystemEventLogWatchdogNum,
		saHpiSystemEventLogWatchdogAction,
		saHpiSystemEventLogWatchdogPreTimerAction,
		saHpiSystemEventLogWatchdogUse,
		saHpiSystemEventLogOemManufacturerIdT,
		saHpiSystemEventLogOemEventData,
		saHpiSystemEventLogUserEventData,
		saHpiSystemEventLogDelete
	}
	STATUS current
	DESCRIPTION 
		"System event group"
	::=  { hpiMIBCompliances 3}

saHpiHotSwapGroup OBJECT-GROUP
	OBJECTS {
		saHpiHotSwapIndicator,
		saHpiHotSwapPowerState,
		saHpiHotSwapResetState,
		saHpiHotSwapState,
		saHpiHotSwapPreviousState,
		saHpiHotSwapEventSeverity,
		saHpiHotSwapInsertTimeout,
		saHpiHotSwapExtractTimeout,
		saHpiHotSwapActionRequest,
		saHpiHotSwapRTP
	}
	STATUS current
	DESCRIPTION
		"Hotswap group"
	::=  { hpiMIBCompliances 4}

saHpiResourceDataRecordGroup OBJECT-GROUP
	OBJECTS {
		saHpiRdrCount,
		saHpiRdrRecordId,
		saHpiRdrType,
		saHpiRdrEntityPath,
		saHpiRdr,
		saHpiRdrId,
		saHpiRdrRTP
	}
	STATUS current
	DESCRIPTION
		"Resource Data Record group"
	::=  { hpiMIBCompliances 5}

saHpiSensorGroup	OBJECT-GROUP
	OBJECTS {
		saHpiSensorCount,
		saHpiSensorIndex,
		saHpiSensorType,
		saHpiSensorCategory,
		saHpiSensorEventsCategoryControl,
		saHpiSensorEventsSupported,
		saHpiSensorStatus,
        	saHpiSensorAssertEvents,
        	saHpiSensorDeassertEvents,
		saHpiSensorIgnore,
		saHpiSensorReadingFormats,
		saHpiSensorIsNumeric,
		saHpiSensorSignFormat,
		saHpiSensorBaseUnits,
		saHpiSensorModifierUnits,
		saHpiSensorModifierUse,
		saHpiSensorFactorsStatic,
		saHpiSensorFactors,
		saHpiSensorFactorsLinearization,
		saHpiSensorPercentage,
		saHpiSensorRangeFlags,
		saHpiSensorHasThresholds,
		saHpiSensorThresholdCapabilities,
		saHpiSensorOEM,
		saHpiSensorRDR
	}
	STATUS current
	DESCRIPTION
		"Sensors groups."
	::=  { hpiMIBCompliances 6}

saHpiSensorReadingCurrentGroup OBJECT-GROUP
	OBJECTS {
		saHpiSensorReadingCurrentValuesPresent,
		saHpiSensorReadingCurrentRaw,
		saHpiSensorReadingCurrentInterpreted,
		saHpiSensorReadingCurrentStatus,
		saHpiSensorReadingCurrentEventStatus
	}
	STATUS current
	DESCRIPTION
		"Current (dynamic) sensor reading."
	::= { hpiMIBCompliances 7}

saHpiSensorReadingMaxGroup OBJECT-GROUP
	OBJECTS {
		saHpiSensorReadingMaxValuesPresent,
		saHpiSensorReadingMaxRaw,
		saHpiSensorReadingMaxInterpreted,
		saHpiSensorReadingMaxStatus,
		saHpiSensorReadingMaxEventStatus
	}
	STATUS current
	DESCRIPTION
		"Manufacturer maximum sensor reading."
	::= { hpiMIBCompliances 8}

saHpiSensorReadingMinGroup OBJECT-GROUP
	OBJECTS {
		saHpiSensorReadingMinValuesPresent,
		saHpiSensorReadingMinRaw,
		saHpiSensorReadingMinInterpreted,
		saHpiSensorReadingMinStatus,
		saHpiSensorReadingMinEventStatus
	}
	STATUS current
	DESCRIPTION
		"Manufacturer minimum sensor reading."
	::= { hpiMIBCompliances 9}

saHpiSensorReadingNominalGroup OBJECT-GROUP
	OBJECTS {
		saHpiSensorReadingNominalValuesPresent,
		saHpiSensorReadingNominalRaw,
		saHpiSensorReadingNominalInterpreted,
		saHpiSensorReadingNominalStatus,
		saHpiSensorReadingNominalEventStatus
	}
	STATUS current
	DESCRIPTION
		"Manufacturer nominal sensor reading."
	::= { hpiMIBCompliances 10}


saHpiSensorReadingNormalMaxGroup OBJECT-GROUP
	OBJECTS {
		saHpiSensorReadingNormalMaxValuesPresent,
		saHpiSensorReadingNormalMaxRaw,
		saHpiSensorReadingNormalMaxInterpreted,
		saHpiSensorReadingNormalMaxStatus,
		saHpiSensorReadingNormalMaxEventStatus
	}
	STATUS current
	DESCRIPTION
		"Manufacturer normal maximum sensor reading."
	::= { hpiMIBCompliances 11}

saHpiSensorReadingNormalMinGroup OBJECT-GROUP
	OBJECTS {
		saHpiSensorReadingNormalMinValuesPresent,
		saHpiSensorReadingNormalMinRaw,
		saHpiSensorReadingNormalMinInterpreted,
		saHpiSensorReadingNormalMinStatus,
		saHpiSensorReadingNormalMinEventStatus
	}
	STATUS current
	DESCRIPTION
		"Manufacturer normal minimum sensor reading."
	::= { hpiMIBCompliances 12}
	
saHpiSensorThdLowCriticalGroup OBJECT-GROUP
	OBJECTS {
		saHpiSensorThdLowCriticalValuesPresent,
		saHpiSensorThdLowCriticalIsReadable,
		saHpiSensorThdLowCriticalIsWritable,
		saHpiSensorThdLowCriticalIsFixed,
		saHpiSensorThdLowCriticalRaw,
		saHpiSensorThdLowCriticalInterpreted
	}
	STATUS current
	DESCRIPTION
		"Threshold values for catastrophic sensor reading at 
		the lower end of the range that does not impact the
		functional status."
	::= { hpiMIBCompliances 13}

saHpiSensorThdLowMajorGroup OBJECT-GROUP
	OBJECTS {
		saHpiSensorThdLowMajorValuesPresent,
		saHpiSensorThdLowMajorIsReadable,
		saHpiSensorThdLowMajorIsWritable,
		saHpiSensorThdLowMajorIsFixed,
		saHpiSensorThdLowMajorRaw,
		saHpiSensorThdLowMajorInterpreted
	}
	STATUS current
	DESCRIPTION
		"Threshold values for severely degraded sensor reading
		at the lower end of the range that does not impact
		the functional status."
	::= { hpiMIBCompliances 14}

saHpiSensorThdLowMinorGroup OBJECT-GROUP
	OBJECTS {
		saHpiSensorThdLowMinorValuesPresent,
		saHpiSensorThdLowMinorIsReadable,
		saHpiSensorThdLowMinorIsWritable,
		saHpiSensorThdLowMinorIsFixed,
		saHpiSensorThdLowMinorRaw,
		saHpiSensorThdLowMinorInterpreted
	}
	STATUS current
	DESCRIPTION
		"Threshold values for degraded sensor reading at the 
		lower end of the range that does not impact the
		functional status."
	::= { hpiMIBCompliances 15}


saHpiSensorThdUpCriticalGroup OBJECT-GROUP
	OBJECTS {
		saHpiSensorThdUpCriticalValuesPresent,
		saHpiSensorThdUpCriticalIsReadable,
		saHpiSensorThdUpCriticalIsWritable,
		saHpiSensorThdUpCriticalIsFixed,
		saHpiSensorThdUpCriticalRaw,
		saHpiSensorThdUpCriticalInterpreted
	}
	STATUS current
	DESCRIPTION
		"Threshold values for catastrophic sensor reading at
		the upper end of the range that does not impact the
		functional status."
	::= { hpiMIBCompliances 16}

saHpiSensorThdUpMajorGroup OBJECT-GROUP
	OBJECTS {
		saHpiSensorThdUpMajorValuesPresent,
		saHpiSensorThdUpMajorIsReadable,
		saHpiSensorThdUpMajorIsWritable,
		saHpiSensorThdUpMajorIsFixed,
		saHpiSensorThdUpMajorRaw,
		saHpiSensorThdUpMajorInterpreted
	}
	STATUS current
	DESCRIPTION
		"Threshold values for severely degraded sensor reading
		at the upper end of the range that does not impact the
		functional status of the sensor."
	::= { hpiMIBCompliances 17}


saHpiSensorThdUpMinorGroup OBJECT-GROUP 
	OBJECTS {
		saHpiSensorThdUpMinorValuesPresent,
		saHpiSensorThdUpMinorIsReadable,
		saHpiSensorThdUpMinorIsWritable,
		saHpiSensorThdUpMinorIsFixed,
		saHpiSensorThdUpMinorRaw,
		saHpiSensorThdUpMinorInterpreted
	}
	STATUS current
	DESCRIPTION
		"Threshold values for degraded sensor reading at the
		upper end of the range that does not impact the
		functional status of the sensor."
	::= { hpiMIBCompliances 18}


saHpiSensorThdPosHysteresisGroup OBJECT-GROUP
	OBJECTS {
		saHpiSensorThdPosHysteresisValuesPresent,
		saHpiSensorThdPosHysteresisIsReadable,
		saHpiSensorThdPosHysteresisIsWritable,
		saHpiSensorThdPosHysteresisIsFixed,
		saHpiSensorThdPosHysteresisRaw,
		saHpiSensorThdPosHysteresisInterpreted
	}
	STATUS current
	DESCRIPTION
		"Threshold values for hysteresis which is the positive
		range over which a change is accepted."
	::= { hpiMIBCompliances 19}


saHpiSensorThdNegHysteresisGroup OBJECT-GROUP
	OBJECTS {
		saHpiSensorThdNegHysteresisValuesPresent,
		saHpiSensorThdNegHysteresisIsReadable,
		saHpiSensorThdNegHysteresisIsWritable,
		saHpiSensorThdNegHysteresisIsFixed,
		saHpiSensorThdNegHysteresisRaw,
		saHpiSensorThdNegHysteresisInterpreted
	}
	STATUS current
	DESCRIPTION
		"Threshold values for hysteresis which is the negative
		range over which a change is accepted."
	::= { hpiMIBCompliances 20}

saHpiCtrlGroup OBJECT-GROUP
	OBJECTS {
		saHpiCtrlCount,
		saHpiCtrlNum,
		saHpiCtrlOutputType,
		saHpiCtrlIgnore,
		saHpiCtrlType,
		saHpiCtrlState,
		saHpiCtrlAttributes,
		saHpiCtrlOem,
		saHpiCtrlTextType,
		saHpiCtrlTextLanguage,
		saHpiCtrlText,
		saHpiCtrlRDR
	}
	STATUS current
	DESCRIPTION
		"Control group."
	::=  { hpiMIBCompliances 21}

saHpiInventoryGroup OBJECT-GROUP
	OBJECTS {
		saHpiInventoryCount,
		saHpiInventoryEirId,
		saHpiInventoryIndex,
		saHpiInventoryRecordType,
		saHpiInventoryValidity,
		saHpiInventoryAttributes,
		saHpiInventoryTextType ,
		saHpiInventoryTextLanguage,
		saHpiInventoryManufacturer,
		saHpiInventoryProductName,
		saHpiInventoryProductVersion,
		saHpiInventoryModelNumber,
		saHpiInventorySerialNumber,
		saHpiInventoryPartNumber,
		saHpiInventoryFileId,
		saHpiInventoryAssetTag,
		saHpiInventoryCustomField,
		saHpiInventoryRDR
	}
	STATUS current
	DESCRIPTION
		"Inventory group."
	::=  { hpiMIBCompliances 22}

saHpiWatchdogGroup OBJECT-GROUP
	OBJECTS {
		saHpiWatchdogCount,
		saHpiWatchdogNum,
		saHpiWatchdogLog ,
		saHpiWatchdogRunning ,
		saHpiWatchdogTimerUse,
		saHpiWatchdogTimerAction,
		saHpiWatchdogPretimerInterrupt,
		saHpiWatchdogPreTimeoutInterval,
		saHpiWatchdogTimerUseExpFlags,
		saHpiWatchdogTimerInitialCount,
		saHpiWatchdogTimerPresentCount,
		saHpiWatchdogTimerReset,
		saHpiWatchdogOem,
		saHpiWatchdogRDR
	}
	STATUS current
	DESCRIPTION
		"Watchdog group."
	::=  { hpiMIBCompliances 23}

saHpiNotificationGroup NOTIFICATION-GROUP
	NOTIFICATIONS {
		saHpiSensorNotification,
		saHpiHotSwapNotification,
		saHpiWatchdogNotification,
		saHpiOEMNotifications,
		saHpiUserNotifications,
		saHpiResourceNotifications,
		saHpiResourceDataRecordNotifications
	}
	STATUS	current
	DESCRIPTION
	"Notification group"
	::=  { hpiMIBCompliances 24}
	
saHpiMIBCompliance MODULE-COMPLIANCE
	STATUS current
	DESCRIPTION
	"The compliance statement for SMIv2 compliance of Platform MIB."
	MODULE
	MANDATORY-GROUPS {
		saHpiEntityGroup,
		saHpiEventGroup,
		saHpiSystemEventGroup,
		saHpiHotSwapGroup,
		saHpiResourceDataRecordGroup,
		saHpiSensorGroup,
		saHpiSensorReadingCurrentGroup,
		saHpiSensorReadingMaxGroup,
		saHpiSensorReadingMinGroup,
		saHpiSensorReadingNominalGroup,
		saHpiSensorReadingNormalMaxGroup,
		saHpiSensorReadingNormalMinGroup,
		saHpiSensorThdLowCriticalGroup,
		saHpiSensorThdLowMajorGroup,
		saHpiSensorThdLowMinorGroup,
		saHpiSensorThdUpCriticalGroup,
		saHpiSensorThdUpMajorGroup,
		saHpiSensorThdUpMinorGroup,
		saHpiSensorThdPosHysteresisGroup,
		saHpiSensorThdNegHysteresisGroup,
		saHpiCtrlGroup,
		saHpiInventoryGroup,
		saHpiWatchdogGroup,
		saHpiNotificationGroup
	}
	::=  { hpiMIBCompliances 25}
END
